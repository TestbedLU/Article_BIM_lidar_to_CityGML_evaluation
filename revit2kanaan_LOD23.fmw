FME workspace revit2kanaan_LOD23.fmw
Title: revit2kanaanLOD23
Description: This workspace is released under the 3-Clause BSD License. 
    Copyright (c) 2017, Lantmäteriet
    All rights reserved.
    Redistribution and use in source and binary forms, with or without modification, are permitted provided that the following conditions are met:
    1. Redistributions of source code must retain the above copyright notice, this list of conditions and the following disclaimer.
    2. Redistributions in binary form must reproduce the above copyright notice, this list of conditions and the following disclaimer in the documentation and/or other materials provided with the distribution.
    3. Neither the name of the copyright holder nor the names of its contributors may be used to endorse or promote products derived from this software without specific prior written permission.
    THIS SOFTWARE IS PROVIDED BY THE COPYRIGHT HOLDERS AND CONTRIBUTORS "AS IS" AND ANY EXPRESS OR IMPLIED WARRANTIES, INCLUDING, BUT NOT LIMITED TO, THE IMPLIED WARRANTIES OF MERCHANTABILITY AND FITNESS FOR A PARTICULAR PURPOSE ARE DISCLAIMED. IN NO EVENT SHALL THE COPYRIGHT HOLDER OR CONTRIBUTORS BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE. 
=-=-=-=-=-=-=-=-=
FME Workspace-fil framtagen av Svensk geoprocess Testdatagrupp, Lantmäteriet. Översätter byggnadsdata i SketchUp-format (*.skp) till XML-fil/filer (*.xml) enligt Svensk geoprocess geodataspecifikationer. Processen bygger på indata från Malmö stad.
    FME Workspace-filen är specifikt utformad för de indata som översätts. Detta innebär att i fallet då indata från annan källa ska översättas behövs sannolikt en modifiering av själva FME-processen för att passa indata i fråga.
    Bör öppnas med FME version 2017.1 eller nyare för att garantera att översättningen fungerar korrekt. 
Geodataspecifikation: 
http://www.lantmateriet.se/sv/Om-Lantmateriet/Samverkan-med-andra/Svensk-geoprocess/specifikationer-och-matningsanvisningar/
UML-modell: 
ftp://ftp.lantmateriet.se/pub/svensk_geoprocess/UML-modell/SvenskGeoprocess_HTML_modell/index.htm
XML-schema: 
http://namespace.lantmateriet.se/svenskgeoprocess/by/3.0_TEST_1/BY_Byggnad.xsd
Mer om testdata för Svensk geoprocess och möjlighet till validering av XML-fil/filer se: http://www.lantmateriet.se/sv/Om-Lantmateriet/Samverkan-med-andra/Svensk-geoprocess/testdata-och-validering/
Vid frågor eller synpunkter, kontakta supporten på svenskgeoprocess@lm.se.
=-=-=-=-=-=-=-=-=
www.lantmateriet.se
History: 2017-08-21,Lantmäteriet,Version 3.0 TEST 1; Skapad

Parameters:
- SourceDataset_REVIT = D\Temp\A40-V-Kanaans-cafe(Grimsta 1-2).ifc   # Source Revit Export File(s)
- DestDataset_GML = D:\Temp\Kanaan_LOD_2_3.gml   # Destination Geography Markup Language (GML) File

Readers:
- REVIT_1: REVIT from $(SourceDataset_REVIT)

Writers:
- GML_1: GML to $(DestDataset_GML)

Note: Kanaan’s Garden Café to LOD2.3 / This workspace is released under the 3-Clause BSD License. For details, see the Description of this workspace. See also https://opensource.org/licenses/BSD-3-Clause / This script reads an IFC model and tranforms it to LOD2.3 CityGML building model geometry (GML 3.1.1). The IFC model is not included with the workbench. / Roof and slab elements are used to get the roof surfaces of the building model. / Slab elements are used to extract the footprint of the building. / The CityGML building model geometry is derived by extruding the footprint of the building and the roof surfaces upwards. The extruded building body is then clipped with the extruded roof surfaces and the original roof surfaces are added to the clipped building. / For suggested detailed LOD definitions (LOD2.3) see: / Biljecki, F., Ledoux, H., Stoter, J., 2016a. An improved LOD specification for 3D building models. Computers, Environment, and Urban Systems, vol. 59, pp. 25-37. https://doi.org/10.3390/ijgi4042842. / The workbench is created with FME version 2017.1.2.1
Roof (reader REVIT_1)
    attributes: element_parent_id char(200), element_id char(200), GlobalId char(200), Name char(200), ObjectType char(200), Tag char(200), Analytical Properties.Absorptance double, Analytical Properties.Roughness double, Constraints.Base Level char(200), Constraints.Base Offset From Level double, Constraints.Cutoff Offset double, Constraints.Related to Mass logical, Constraints.Room Bounding logical, Construction.Default Thickness double, Construction.Fascia Depth double, Construction.Maximum Ridge Height double, Construction.Rafter Cut char(200), Dimensions.Area double, Dimensions.Thickness double, Dimensions.Volume double, Graphics.Coarse Scale Fill Color integer, Identity Data.Assembly Code char(200), Identity Data.Assembly Description char(200), Phasing.Phase Created char(200), Pset_RoofCommon.IsExternal logical, Pset_RoofCommon.ProjectedArea double, Pset_RoofCommon.Reference char(200), Pset_RoofCommon.TotalArea double, Pset_ManufacturerTypeInformation.Manufacturer char(200), Pset_ManufacturerTypeInformation.ModelLabel char(200),
      Pset_ManufacturerTypeInformation.ModelReference char(200), Pset_ManufacturerTypeInformation.ProductionYear char(200)
    -> AreaCalculator_4
Tester_mainRoofentranceRoof
    TEST_MODE = Automatic
    TEST_DESCRIPTION = ""
    BOOL_OP = OR
    TEST_CLAUSE = TEST @Value(_count_roofSorter) < 1
    PASSED -> IFC2CityGML_Geometryconverter_parts_roof [GeometryPartExtractor_2_Input]
    FAILED -> IFC2CityGML_Geometryconverter_parts_roof [GeometryPartExtractor_2_Input]
Note: Aggregator_roof : Input
Junction_10
    -> Junction_11
Note: Aggregator_allRoofs_2 : Input
Junction_14
    -> Junction_15
Note: Aggregator_roof : Input
Junction_12
    -> Junction_13
Slab (reader REVIT_1)
    attributes: element_parent_id char(200), element_id char(200), GlobalId char(200), Name char(200), ObjectType char(200), Tag char(200), OverallHeight double, OverallWidth double, Analytical Properties.Absorptance double, Analytical Properties.Roughness double, BaseQuantities.GrossArea double, BaseQuantities.GrossVolume double, BaseQuantities.Perimeter double, BaseQuantities.Width double, Constraints.Base Level char(200), Constraints.Base Offset From Level double, Constraints.Cutoff Offset double, Constraints.Height Offset From Level double, Constraints.Level char(200), Constraints.Related to Mass logical, Constraints.Room Bounding logical, Construction.Default Thickness double, Construction.Fascia Depth double, Construction.Function char(200), Construction.Maximum Ridge Height double, Construction.Rafter Cut char(200), Construction.Rafter or Truss char(200), Construction.Thickness double, Dimensions.Area double, Dimensions.Perimeter double,
      Dimensions.Slope double, Dimensions.Thickness double, Dimensions.Volume double, Graphics.Coarse Scale Fill Color double, Identity Data.Assembly Code char(200), Identity Data.Assembly Description char(200), Materials and Finishes.Structural Material char(200), Phasing.Phase Created char(200), Pset_RoofCommon.IsExternal logical, Pset_RoofCommon.ProjectedArea double, Pset_RoofCommon.Reference char(200), Pset_RoofCommon.TotalArea double, Pset_SlabCommon.IsExternal logical, Pset_SlabCommon.LoadBearing logical, Pset_SlabCommon.Reference char(200), Pset_ManufacturerTypeInformation.Manufacturer char(200), Pset_ManufacturerTypeInformation.ModelLabel char(200), Pset_ManufacturerTypeInformation.ModelReference char(200), Pset_ManufacturerTypeInformation.ProductionYear char(200)
    -> AttributeExposer
    -> Tester
Note: Aggregator_allRoofs_2 : Input
Junction_16
    -> Junction_17
Note: Aggregator_allRoofs_2 : Input
Junction_18
    -> Junction_19
Note: HullReplacer : Hull
Junction_2
    -> Clipper_3 [CLIPPER]
FeatureColorSetter
    FILL_COLOR = 0.666667,0.333333,0
    COLOR = 0.666667,0.333333,0
    MODE = Fixed
    COLORED -> GeometryExtractor
Note: Clipping the extruded footprint of the / building to remove parts above the roof.
Clipper_buildingRoof
    MISSING_VAL_MODE = Compute
    CLIP_TYPE = Multiple Clippers
    VAL_SOURCE = Clippee Only
    MEASURE_TYPE = Continuous
    LINES_AS_SEGMENTS = No
    BOUNDARY_CASES = Treat as Inside
    PRESERVE_CLIPPEE_EXTENTS = No
    CLIPPED_ATTR = _clipped
    CREATE_AGGREGATES = Yes
    OUTSIDE -> IFC2CityGML_Geometryconverter_parts [GeometryPartExtractor_2_Input]
    <REJECTED> -> Clipper__Rejected_
GeometryExtractor
    OGCVERSION = 1.2
    OGEOSMS_URL_PREFIX = http://maps.google.com/?q=
    OGC_WKT_PRECISION_DISPLAY = Shortened 64-bit
    PREFER_POLYGON_OVER_SURFACE = No
    KIND_LONG = GML v3.1.1
    ATTR = _geometry
    OMIT_NAMESPACES_DISPLAY = No
    REMOVE_GEOMETRY = No
    -> GeometryExtractor_Output
    -> NewFeatureType (writer GML_1)
    <REJECTED> -> GeometryExtractor__Rejected_
NewFeatureType (writer GML_1)
GeometryExtractor_Output: Inspector
GeometryExtractor__Rejected_: Inspector
Clipper__Rejected_: Inspector

Bookmark: Sorting roofs by area
AreaCalculator_4
    AREA_TYPE = Plane Area
    AREA_ATTR = _area_roofSorter
    MULT = 1
    -> Sorter_2
    <REJECTED> -> AreaCalculator_4__Rejected_
AreaCalculator_4__Rejected_: Inspector
Sorter_2
    SORT_PARM = _area_roofSorter NUMERIC DESCENDING
    SORTED -> Counter_roofSorter
Counter_roofSorter
    DOMAIN = counter
    START = 0
    SCOPE = Local
    CNT_ATTR = _count_roofSorter
    -> Tester_mainRoofentranceRoof

Bookmark: Main roof
IFC2CityGML_Geometryconverter_parts_roof
    -> NormalVectorFinder_roof [CoordinateExtractor_Input]
NormalVectorFinder_roof
    NormVec_Output -> TestFilter_roofUpLooking
TestFilter_roofUpLooking
    TEST_LIST = BOOL_OP,OR,COMPOSITE_TEST,<Unused>,TEST_CLAUSE,"TEST @Value(_vz) > 0",upLooking
    DEFAULT_VALUE = <UNFILTERED>
    upLooking -> AreaCalculator_3

Bookmark: Filter out small parts
  Filter out small parts around the chimneys that are uplooking and would be included in one of the roof surfaces even if they are "holes" and not surfaces.
AreaCalculator_3
    AREA_TYPE = Plane Area
    AREA_ATTR = _area_roof_up
    MULT = 1
    -> Tester_2
Tester_2
    TEST_MODE = Automatic
    TEST_DESCRIPTION = ""
    BOOL_OP = OR
    TEST_CLAUSE = TEST @Value(_area_roof_up) > 0.1
    PASSED -> TestFilter_5

Bookmark: To split main roof into two sides
TestFilter_5
    TEST_LIST = BOOL_OP,OR,COMPOSITE_TEST,<Unused>,TEST_CLAUSE,"TEST @Value(_vx) > 0",posNormX
    DEFAULT_VALUE = <UNFILTERED>
    posNormX -> Aggregator_3
    <UNFILTERED> -> Aggregator_4
Aggregator_3
    SEP = ,
    AGGREGATE_TYPE = Homogeneous Collection (If Possible)
    ACCUM_ATTRS_NAME = Use Attributes From One Feature
    ORDERED = No
    GROUP_BY = element_id
    MODE = Geometry - Assemble One Level
    AGGREGATE -> HullReplacer_mainRoof2
    AGGREGATE -> Counter_roofID
HullReplacer_mainRoof2
    HULLTYPE_PARAM = Convex ()
    3DMODE_PARAM = Automatic
    HULL -> Junction_10
Aggregator_4
    SEP = ,
    AGGREGATE_TYPE = Homogeneous Collection (If Possible)
    ACCUM_ATTRS_NAME = Use Attributes From One Feature
    ORDERED = No
    GROUP_BY = element_id
    MODE = Geometry - Assemble One Level
    AGGREGATE -> HullReplacer_mainRoof1
    AGGREGATE -> Counter_roofID
HullReplacer_mainRoof1
    HULLTYPE_PARAM = Convex ()
    3DMODE_PARAM = Automatic
    HULL -> Junction_12

Bookmark: Creating footprint of merged roof surfaces
  Used to clip the footprint created from the slab since parts of the slabs are outside the roof. These parts can not be included in the 3D model.
Note: HullReplacer_mainRoof2 : Hull
Junction_11
    -> Aggregator_roof
Note: HullReplacer_mainRoof1 : Hull
Junction_13
    -> Aggregator_roof
Note: TestFilter_2 : longSide
Junction_7
    -> Aggregator_roof
Note: TestFilter_2 : <Unfiltered>
Junction_9
    -> Aggregator_roof
SurfaceFootprintReplacer
    LIGHT_Z = 1
    OFFSET_Z = 0
    LIGHT_Y = 0
    SHADOW_MODE = Overhead Shadow
    LIGHT_X = 0
    FOOTPRINT -> HullReplacer_roofSurfaces
Note: To remove spikes in the footprint. / NB!!!! NOT EXACT FOOTPRINT!!!! / Ony used to check which parts of / the building footprint that is inside / the roof's footprint. / Difference is that the concave are / slightly rounded (not 90 degree)
HullReplacer_roofSurfaces
    HULLTYPE_PARAM = Concave )(
    ALPHA = 0.1
    3DMODE_PARAM = Automatic
    HULL -> Junction
Note: Clipper_3 : Clipper
Junction
    -> Junction_2

Bookmark: From mesh to polygons for roof surfaces
  Creating polygons of the two main roof surfaces and the roof over the main entrance
Note: Creating IDs for the roof surfaces / to join with footprint in Pythoncaller.
Counter_roofID
    DOMAIN = counter
    START = 0
    SCOPE = Local
    CNT_ATTR = _roofID
    -> AttributeKeeper
AttributeKeeper
    KEEP_ATTRS = element_id,Tag,GlobalId,element_parent_id,Name,_roofID,ObjectType
    -> SurfaceFootprintReplacer_3
    -> PythonCaller_roofPolygonHandler
SurfaceFootprintReplacer_3
    LIGHT_Z = 1
    OFFSET_Z = 0
    LIGHT_Y = 0
    SHADOW_MODE = Overhead Shadow
    LIGHT_X = 0
    FOOTPRINT -> AttributeCreator
AttributeCreator
    ATTR_TABLE = SET_TO footPrint = 1
    -> Generalizer
Generalizer
    ALG_TEXT = Douglas (Generalize)
    PRESERVE = No
    TOLERANCE = 0.5
    -> PythonCaller_roofPolygonHandler
PythonCaller_roofPolygonHandler
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.footPrints = {} # Dict with surface footprint polygons
              self.roof = {} # Dict with roof polygons

          def input(self,feature):
              # Saving footprints and roofs in separate lists
              if feature.getAttribute('footPrint'):
                  self.footPrints[feature.getAttribute('_roofID')] = feature
              else:
                  self.roof[feature.getAttribute('_roofID')] = feature

          def close(self):
              # Iterating over all the footprint of all roof surfaces to add
              # z-coordinate derived from the roof surface
              for roofIdKey in self.footPrints:
                  tempFootPrint = self.footPrints[roofIdKey]
                  tempRoof = self.roof[roofIdKey]

                  # To get list of point from all the boundary
                  footPolyLine = tempFootPrint.getGeometry().getBoundaryAsCurve()
                  footPolyPoints = footPolyLine.getPoints()
                  # To get ALL coordinates in the roof surfaces (NB, they are mesh)
                  roofPolyCoords = tempRoof.getAllCoordinates()

                  # Iterating over all points in the roof footprint perimeter to
                  # add z-coordinate and "lift" the footprint to the roof level
                  outPoints = [] # For saving points with added z-values
                  for p in footPolyPoints:
                      (xp, yp, zp) = p.getXYZ()
                      eps = 0.1 # Max distance in the xy-plane to consider points to be equal
                      idx = 0 # index for current point in the roof surface.
                      tempPoint = roofPolyCoords[idx]
                      while sqrt((xp-tempPoint[0])**2 + (yp-tempPoint[1])**2) > eps:
                          idx += 1
                          tempPoint = roofPolyCoords[idx]

                      # The new point (with added z-value)
                      np = (xp, yp, tempPoint[2])
                      # and added to the list of points (as (x,y,z)-tuple)
                      outPoints.append(np)

                  # Creating a new Feature with the adjusted roof
                  nl = fmeobjects.FMELine(outPoints)
                  np = fmeobjects.FMEPolygon(nl)
                  nf = fmeobjects.FMEFeature()
                  nf.setGeometry(np)
                  nf.setAttribute('_roofID', tempRoof.getAttribute('_roofID'))
                  nf.setAttribute('element_id', tempRoof.getAttribute('element_id'))
                  nf.setAttribute('element_parent_id', tempRoof.getAttribute('element_parent_id'))
                  nf.setAttribute('Name', tempRoof.getAttribute('Name'))
                  nf.setAttribute('Tag', tempRoof.getAttribute('Tag'))

                  self.pyoutput(nf)
    -> Extruder_mainRoofEntranceRoof
    -> Junction_14

Bookmark: All roof surfaces
Note: PythonCaller_roofPolygonHandler : Output
Junction_15
    -> Aggregator_allRoofs_2
    -> FeatureColorSetter
Note: HullReplacer_entranceRoof_2 : Hull
Junction_17
    -> Aggregator_allRoofs_2
    -> FeatureColorSetter
Note: HullReplacer_entranceRoof : Hull
Junction_19
    -> Aggregator_allRoofs_2
    -> FeatureColorSetter
Note: TestFilter_2 : <Unfiltered>
Junction_21
    -> Aggregator_allRoofs_2
    -> GeometryCoercer_2

Bookmark: Extruding roof surfaces upwards
  Extruding roof surfaces upwards to clip (remove) the part of the extruded footprint that is "outside" the building.
Extruder_mainRoofEntranceRoof
    DISTANCE = -10
    DIRECTION = Specified
    EXTRUSION_Y = 0.0
    EXTRUSION_X = 0.0
    EXTRUSION_Z = 10
    EXTRUDED -> Aggregator_allRoofs
Extruder_entrances
    DIRECTION = Specified
    EXTRUSION_Y = 0.0
    EXTRUSION_X = 0.0
    EXTRUSION_Z = 10
    EXTRUDED -> Aggregator_allRoofs
Aggregator_allRoofs
    SEP = ,
    AGGREGATE_TYPE = Homogeneous Collection (If Possible)
    ACCUM_ATTRS_NAME = Use Attributes From One Feature
    ORDERED = No
    MODE = Geometry - Assemble One Level
    AGGREGATE -> Clipper_buildingRoof [CLIPPER]

Bookmark: Roofs from slab - to get roofs that are modelled as slabs
AttributeExposer
    ATTR_LIST = PredefinedType
    -> Tester_slab_ROOF
Tester_slab_ROOF
    TEST_MODE = Automatic
    TEST_DESCRIPTION = ""
    BOOL_OP = OR
    TEST_CLAUSE = TEST @Value(PredefinedType) = ROOF
    PASSED -> IFC2CityGML_Geometryconverter_parts_slab [GeometryPartExtractor_2_Input]
IFC2CityGML_Geometryconverter_parts_slab
    -> NormalVectorFinder_slab [CoordinateExtractor_Input]
NormalVectorFinder_slab
    NormVec_Output -> AreaCalculator
AreaCalculator
    AREA_TYPE = Plane Area
    AREA_ATTR = _area_roffslab
    MULT = 1
    -> TestFilter_upLookingMainRoof
TestFilter_upLookingMainRoof
    TEST_LIST = BOOL_OP,OR,COMPOSITE_TEST,<Unused>,TEST_CLAUSE,"TEST @Value(_vz) > 0.01",upLooking
    DEFAULT_VALUE = <UNFILTERED>
    upLooking -> TestFilter_mainRoofLeaningSlab
TestFilter_mainRoofLeaningSlab
    TEST_LIST:
      BOOL_OP,AND,COMPOSITE_TEST,<Unused>,TEST_CLAUSE,"TEST @Evaluate(@abs(@Value(_vx))) > 0
      TEST @Evaluate(@abs(@Value(_vy))) > 0",leaningSlab
    DEFAULT_VALUE = <UNFILTERED>
    leaningSlab -> Tester_roofDecorations
Tester_roofDecorations
    TEST_MODE = Automatic
    TEST_DESCRIPTION = ""
    BOOL_OP = OR
    TEST_CLAUSE = TEST @Value(_area_roffslab) > 1
    PASSED -> TestFilter_2
TestFilter_2
    TEST_LIST:
      BOOL_OP,OR,COMPOSITE_TEST,<Unused>,TEST_CLAUSE,"TEST @Value(element_id) = 26DuHjHNH16uI76M5QoRa2
      TEST @Value(element_id) = 26DuHjHNH16uI76M1QoRa2
      TEST @Value(element_id) = 26DuHjHNH16uI76MPQoRa2
      TEST @Value(element_id) = 26DuHjHNH16uI76MTQoRa2",longSide
    DEFAULT_VALUE = <UNFILTERED>
    longSide -> Tester_3
    longSide -> Junction_5
    <UNFILTERED> -> Extruder_entrances
    <UNFILTERED> -> Junction_8
    <UNFILTERED> -> Junction_20
Tester_3
    TEST_MODE = Automatic
    TEST_DESCRIPTION = ""
    BOOL_OP = OR
    TEST_CLAUSE = TEST @Value(_vx) < 0
    PASSED -> HullReplacer_entranceRoof_2
    FAILED -> HullReplacer_entranceRoof
HullReplacer_entranceRoof_2
    HULLTYPE_PARAM = Convex ()
    3DMODE_PARAM = Automatic
    HULL -> Extruder_entrances
    HULL -> Junction_16
HullReplacer_entranceRoof
    HULLTYPE_PARAM = Convex ()
    3DMODE_PARAM = Automatic
    HULL -> Extruder_entrances
    HULL -> Junction_18
Note: Aggregator_roof : Input
Junction_5
    -> Junction_7
Note: Aggregator_roof : Input
Junction_8
    -> Junction_9
Note: Aggregator_allRoofs_2 : Input
Junction_20
    -> Junction_21

Bookmark: Aggregating all roof surfaces
Aggregator_roof
    SEP = ,
    AGGREGATE_TYPE = Homogeneous Collection (If Possible)
    ACCUM_ATTRS_NAME = Use Attributes From One Feature
    ORDERED = No
    MODE = Geometry - Assemble One Level
    AGGREGATE -> SurfaceFootprintReplacer

Bookmark: Just to get highest point of roof
  Using highest point of roof later to remove remaining artefacts from the clipped solid
Aggregator_allRoofs_2
    SEP = ,
    AGGREGATE_TYPE = Homogeneous Collection (If Possible)
    ACCUM_ATTRS_NAME = Use Attributes From One Feature
    ORDERED = No
    MODE = Geometry - Assemble One Level
    AGGREGATE -> CoordinateExtractor
CoordinateExtractor
    MODE = All Coordinates
    LIST_NAME = _roofCoords
    -> ListRangeExtractor
ListRangeExtractor
    MAX = _max_roof_z
    MIN = _min_roof_z
    SRC_LIST = _roofCoords{}.z
    -> AttributeKeeper_2
AttributeKeeper_2
    KEEP_ATTRS = _max_roof_z
    -> GeometryRemover
GeometryRemover
    -> PythonCaller_artefactRemover_2

Bookmark: Handling artefacts in the 3D model that are created when clipping the extruded footprint
  Some artefacts, due to gaps between roof surfaces, creates high outliers in the 3D model. These must be removed.
GeometryCoercer_2
    GQUERY:
      for $geom in //geometry
      where $geom/count(parent::geometry) = 0
      return number($geom/@fme_id)
    KIND = fme_polygon
    COERCED -> FeatureColorSetter
IFC2CityGML_Geometryconverter_parts
    -> NormalVectorFinder [CoordinateExtractor_Input]
NormalVectorFinder
    NormVec_Output -> TestFilter
TestFilter
    TEST_LIST = BOOL_OP,OR,COMPOSITE_TEST,<Unused>,TEST_CLAUSE,"TEST @Value(_vz) > 0",upLooking
    DEFAULT_VALUE = <UNFILTERED>
    <UNFILTERED> -> GeometryCoercer
Note: Needs polygons for the PythonCaller
GeometryCoercer
    GQUERY:
      for $geom in //geometry
      where $geom/count(parent::geometry) = 0
      return number($geom/@fme_id)
    KIND = fme_polygon
    COERCED -> PythonCaller_artefactRemover_2
Note: Removing artefacts in data due to / gaps between triangles.
PythonCaller_artefactRemover_2
    PYTHONSYMBOL = FeatureProcessor
    PYTHONSOURCE:
      import fme
      import fmeobjects

      # Template Class Interface:
      # When using this class, make sure its name is set as the value of
      # the 'Class or Function to Process Features' transformer parameter
      class FeatureProcessor(object):
          def __init__(self):
              self.surfaces = [] # Dict with surface footprint polygons
              self.roofTop = -9999 # Z-coordinate of roof top

          def input(self,feature):
              # Saving all surfaces in list and extracting max roof from the "other" feature
              if feature.hasGeometry():
                  self.surfaces.append(feature)
              else:
                  self.roofTop = float(feature.getAttribute('_max_roof_z'))

          def close(self):

              maxDist = 0.2 # Max allowed dist between point to keep a polygon

              # Iterating over all featuresd and adding max z-roof as attribute
              for s in self.surfaces:
                  geo = s.getGeometry()
                  boundary = geo.getBoundaryAsCurve()
                  pointList = boundary.getPoints()
                  xyzList = [p.getXYZ() for p in pointList]

                  del geo
                  del boundary
                  del pointList

                  outCo = [] # List of adjusted coordinates (top removed)
                  LastHigh = xyzList[-1][2] # For keeping track of last high in case > 1
                  # To check if there are two high coords in a row. If there are two high,
                  # check the distance. If distance is short it is a spike and shall be
                  # removed (z-coord chanegd to previous z). If dist is large the entire
                  # polygon will be removed.
                  prevHigh = False
                  remove = False # Flag stating if a polygon shall be removed or not

                  # Iterating over all coordinates to move "high" to "correct" level = same
                  # z-coord as previous point (or removing entire polygon)
                  for idx, tempCo in enumerate(xyzList):
                      currHigh = tempCo[2]
                      if currHigh >= self.roofTop:
                          outCo.append((xyzList[idx][0], xyzList[idx][1], LastHigh))
                          # Checking dist from previous if also previous was high.
                          if prevHigh:
                              remove = ((xyzList[idx][0]-xyzList[idx-1][0])**2 + (xyzList[idx][1]-xyzList[idx-1][1])**2)**0.5 > maxDist
                          prevHigh = True

                      else:
                           LastHigh = currHigh
                           outCo.append(tempCo)
                           prevHigh = False

                  if not remove:
                      nl = fmeobjects.FMELine(outCo)
                      nfa = fmeobjects.FMEFace(nl, fmeobjects.FME_CLOSE_3D_AVERAGE_MODE)

                      nf = fmeobjects.FMEFeature()
                      nf.setGeometry(nfa)
                      self.pyoutput(nf)
    -> GeometryExtractor

Bookmark: Building footprint
  Creating the building footprint from the slabs.
  NB, part of the slabs are "outside" the roof ans needs to be cut before the 3D model can be created.
Note: Main slab for LOD2.3
Tester
    TEST_MODE = Automatic
    TEST_DESCRIPTION = ""
    BOOL_OP = OR
    TEST_CLAUSE = TEST @Value(element_id) = 2rkyqsD31AQvoI1f_vEduY
    PASSED -> IFC2CityGML_Geometryconverter_parts_footPrint [GeometryPartExtractor_2_Input]
IFC2CityGML_Geometryconverter_parts_footPrint
    -> NormalVectorFinder_mainSlab [CoordinateExtractor_Input]
NormalVectorFinder_mainSlab
    NormVec_Output -> TestFilter_buildingFootPrintUpLooking
TestFilter_buildingFootPrintUpLooking
    TEST_LIST = BOOL_OP,OR,COMPOSITE_TEST,<Unused>,TEST_CLAUSE,"TEST @Value(_vz) > 0",upLooking
    DEFAULT_VALUE = <UNFILTERED>
    upLooking -> AttributeRemover
AttributeRemover
    REMOVE_ATTRS = Dimensions.Perimeter,_vy1,Constraints.Cutoff Offset,_x2,Constraints.Base Offset From Level,_vx0,_vz1,Construction.Function,BaseQuantities.Width,Construction.Rafter Cut,Dimensions.Volume,_vz0,Dimensions.Slope,_z2,Constraints.Room Bounding,Construction.Fascia Depth,Constraints.Related to Mass,Dimensions.Thickness,Constraints.Base Level,Constraints.Level,_z1,BaseQuantities.GrossArea,Analytical Properties.Absorptance,Construction.Default Thickness,_y1,_x1,_vy0,BaseQuantities.Perimeter,Construction.Maximum Ridge Height,BaseQuantities.GrossVolume,_vx1,_y2,Construction.Rafter or Truss,Analytical Properties.Roughness,Constraints.Height Offset From Level,Dimensions.Area,Construction.Thickness,_x0,_y0
    -> SurfaceFootprintReplacer_2
SurfaceFootprintReplacer_2
    LIGHT_Z = 1
    OFFSET_Z = 0
    LIGHT_Y = 0
    SHADOW_MODE = Overhead Shadow
    LIGHT_X = 0
    FOOTPRINT -> Clipper_3 [CLIPPEE]

Bookmark: Extruding footprint of the building
  Clipping the part of the footprint that is outside the roof (clipper extracted from footprint of roof: HullReplacer:Hull)
Clipper_3
    MISSING_VAL_MODE = Compute
    CONNECT_Z_MODE = First Wins
    ATTR_CONFLICT_RES = Use Clippee
    CLIP_TYPE = Multiple Clippers
    VAL_SOURCE = Clippee Only
    DEFAULT_VAL = 0
    MEASURE_TYPE = Continuous
    LINES_AS_SEGMENTS = No
    BOUNDARY_CASES = Treat as Inside
    PRESERVE_CLIPPEE_EXTENTS = No
    ATTR_ACCUM_MODE = Merge Clipper
    CLIPPED_ATTR = _clipped
    CREATE_AGGREGATES = Yes
    INSIDE -> Extruder_footprint
    <REJECTED> -> Clipper_3__Rejected_
Extruder_footprint
    DIRECTION = Specified
    EXTRUSION_Y = 0.0
    EXTRUSION_X = 0.0
    EXTRUSION_Z = 10
    EXTRUDED -> Clipper_buildingRoof [CLIPPEE]
Clipper_3__Rejected_: Inspector

FME custom transformer NormalVectorFinder

CoordinateExtractor_Input (input)
    -> CoordinateCounter
Note: Note that there are wall surfaces (beloning to "Takplan" in KTH where index 0 is in a vertical line with both first and second last index ont eh line i.e. the normals arr not correct.
NormVec_Output (output)

Bookmark: Calculate Normal Vector (_vx, _vy, _vz)
  There was a special case with one outer wall surface (see notes) which gave wrong orientation due to concave shape. This version is using coordinates with index 0, 1, (nbr coords -4) to test if that solves the problem. See notes for more details.
Note: Need to know the number of / coordinates to find the second / last.
CoordinateCounter
    CNT_ATTR = _coordcount_normal_vector
    -> CoordinateExtractor_7
CoordinateExtractor_7
    X_ATTR = _x0
    IND = 0
    Y_ATTR = _y0
    Z_ATTR = _z0
    Z_DEFAULT = -9999
    -> CoordinateExtractor_8
CoordinateExtractor_8
    X_ATTR = _x1
    IND = 1
    Y_ATTR = _y1
    Z_ATTR = _z1
    Z_DEFAULT = -9999
    -> CoordinateExtractor_9
CoordinateExtractor_9
    X_ATTR = _x2
    IND = @Value(_coordcount_normal_vector)-2
    Y_ATTR = _y2
    Z_ATTR = _z2
    Z_DEFAULT = -9999
    -> AttributeCreator_5
AttributeCreator_5
    ATTR_LIST = _vx0,@Evaluate(@Value(_x1)-@Value(_x0)),_vy0,@Evaluate(@Value(_y1)-@Value(_y0)),_vz0,@Evaluate(@Value(_z1)-@Value(_z0)),_vx1,@Evaluate(@Value(_x2)-@Value(_x0)),_vy1,@Evaluate(@Value(_y2)-@Value(_y0)),_vz1,@Evaluate(@Value(_z2)-@Value(_z0))
    -> AttributeCreator_6
AttributeCreator_6
    ATTR_LIST = _vx,@Evaluate(@Value(_vy0)*@Value(_vz1)-@Value(_vz0)*@Value(_vy1)),_vy,@Evaluate(@Value(_vz0)*@Value(_vx1)-@Value(_vx0)*@Value(_vz1)),_vz,@Evaluate(@Value(_vx0)*@Value(_vy1)-@Value(_vy0)*@Value(_vx1))
    -> AttributeRemover
AttributeRemover
    REMOVE_ATTRS = _coordcount_normal_vector
    -> NormVec_Output (output)

Bookmark: Calculate Normal Vector (_vx, _vy, _vz)
CoordinateExtractor
    X_ATTR = _x0
    IND = 0
    Y_ATTR = _y0
    Z_ATTR = _z0
    Z_DEFAULT = -9999
    -> CoordinateExtractor_2
CoordinateExtractor_2
    X_ATTR = _x1
    IND = 1
    Y_ATTR = _y1
    Z_ATTR = _z1
    Z_DEFAULT = -9999
    -> CoordinateExtractor_3
CoordinateExtractor_3
    X_ATTR = _x2
    IND = 3
    Y_ATTR = _y2
    Z_ATTR = _z2
    Z_DEFAULT = -9999
    -> AttributeCreator
AttributeCreator
    ATTR_LIST = _vx0,@Evaluate(@Value(_x1)-@Value(_x0)),_vy0,@Evaluate(@Value(_y1)-@Value(_y0)),_vz0,@Evaluate(@Value(_z1)-@Value(_z0)),_vx1,@Evaluate(@Value(_x2)-@Value(_x0)),_vy1,@Evaluate(@Value(_y2)-@Value(_y0)),_vz1,@Evaluate(@Value(_z2)-@Value(_z0))
    -> AttributeCreator_2
AttributeCreator_2
    ATTR_LIST = _vx,@Evaluate(@Value(_vy0)*@Value(_vz1)-@Value(_vz0)*@Value(_vy1)),_vy,@Evaluate(@Value(_vz0)*@Value(_vx1)-@Value(_vx0)*@Value(_vz1)),_vz,@Evaluate(@Value(_vx0)*@Value(_vy1)-@Value(_vy0)*@Value(_vx1))

FME custom transformer IFC2CityGML_Geometryconverter_parts

GeometryPartExtractor_2_Input (input)
    -> GeometryPartExtractor_2
Note: Check that geometry name is solid
GeometryPartExtractor_2
    GQUERY:
      for $geom in //geometry
      where $geom/@fme_geometry_name = 'Body'
      return number($geom/@fme_id)
    EXTRACTTYPE_PARAM = Extract
    PROCESSED -> GeometryCoercer_2
    UNTOUCHED -> GeometryCoercer_2
Note: Check for geometry type IFMEExtrusion OR IFMEBRepSolid
GeometryCoercer_2
    GQUERY:
      for $geom in //geometry
      where $geom/@fme_geometry_type = 'IFMEExtrusion'
      or $geom/@fme_geometry_type = 'IFMEBRepSolid'
      return number($geom/@fme_id)
    KIND = fme_composite_surface
    COERCED -> Deaggregator
    UNTOUCHED -> Deaggregator
Note: Changed split compostites to YES
Deaggregator
    EXPLODE_INSTANCES = No
    GEOM_NAME_FIELD = _geometry_name
    MODE = Flatten All Levels
    LIST_ATTR_MODE_LOOKUP = LEAN
    SPLIT_COMPOSITES = Yes
    DEAGGREGATED -> GeometryRefiner
Note: Keep this or not?
GeometryRefiner
    -> Output (output)
Output (output)

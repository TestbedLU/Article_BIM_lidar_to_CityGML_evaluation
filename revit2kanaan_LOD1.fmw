FME workspace revit2kanaan_LOD1.fmw
Title: revit2kanaan

Parameters:
- SourceDataset_REVIT = D:\Temp\A40-V-Kanaans-caf(Grimsta 1-2).ifc   # Source Revit Export File(s)
- DestDataset_GML = D:\Temp\Kanaan_LOD_1_2.gml   # Destination Geography Markup Language (GML) File

Readers:
- REVIT_1: REVIT from $(SourceDataset_REVIT)

Writers:
- GML_1: GML to $(DestDataset_GML)

Note: Kanaan’s Garden Café to LOD1 / This workspace is released under the 3-Clause BSD License. For details, see the Description of this workspace. See also https://opensource.org/licenses/BSD-3-Clause / This script reads an IFC model and tranforms it to LOD1 CityGML building model geometry (GML 3.1.1). The IFC model is not included with the workbench. / Roof elements are used to derive the height of the building model. / Wall elements are used to extract teh extent of the building model / Ground level of the building is derived from the stair elements of the IFC model. / The workbench is created with FME version 2017.1.2.1
Note: To find ground level
Stair (reader REVIT_1)
    attributes: element_parent_id char(200), element_id char(200), GlobalId char(200), Name char(200), ObjectType char(200), Tag char(200), ShapeType char(200), Constraints.Base Level char(200), Constraints.Base Offset double, Constraints.Top Level char(200), Constraints.Top Offset double, Construction.Extend Below Base double, Construction.Function char(200), Construction.Landing Overlap double, Construction.Monolithic Stairs logical, Construction.Underside of Winder char(200), Dimensions.Actual Number of Risers integer, Dimensions.Actual Riser Height double, Dimensions.Actual Tread Depth double, Dimensions.Desired Number of Risers integer, Dimensions.Width double, Graphics.Break Symbol in Plan logical, Graphics.Down arrow logical, Graphics.Down label logical, Graphics.Down text char(200), Graphics.Show Up arrow in all views logical, Graphics.Text Font char(200), Graphics.Text Size double, Graphics.Up arrow logical, Graphics.Up label logical,
      Graphics.Up text char(200), Identity Data.Assembly Code char(200), Identity Data.Assembly Description char(200), Materials and Finishes.Stringer Material char(200), Materials and Finishes.Tread Material char(200), Phasing.Phase Created char(200), Pset_StairCommon.IsExternal logical, Pset_StairCommon.NumberOfRiser integer, Pset_StairCommon.NumberOfTreads integer, Pset_StairCommon.Reference char(200), Pset_StairCommon.RiserHeight double, Pset_StairCommon.TreadLength double, Risers.Begin with Riser logical, Risers.End with Riser logical, Risers.Maximum Riser Height double, Risers.Riser Thickness double, Risers.Riser to Tread Connection char(200), Risers.Riser Type char(200), Stringers.Landing Carriage Height double, Stringers.Left Stringer char(200), Stringers.Middle Stringers char(200), Stringers.Open Stringer Offset double, Stringers.Right Stringer char(200), Stringers.Stringer Carriage Height double, Stringers.Stringer Height double, Stringers.Stringer Thickness double, Stringers.Trim Stringers at Top char(200), Treads.Apply Nosing Profile char(200), Treads.Minimum Tread Depth double, Treads.Nosing Length double,
      Treads.Nosing Profile char(200), Treads.Tread Thickness double, Pset_ManufacturerTypeInformation.Manufacturer char(200), Pset_ManufacturerTypeInformation.ModelLabel char(200), Pset_ManufacturerTypeInformation.ModelReference char(200), Pset_ManufacturerTypeInformation.ProductionYear char(200)
    -> TestFilter_3
Note: Aggregator : Input
Junction
    -> Junction_2
Roof (reader REVIT_1)
    attributes: element_parent_id char(200), element_id char(200), GlobalId char(200), Name char(200), ObjectType char(200), Tag char(200), Analytical Properties.Absorptance double, Analytical Properties.Roughness double, Constraints.Base Level char(200), Constraints.Base Offset From Level double, Constraints.Cutoff Offset double, Constraints.Related to Mass logical, Constraints.Room Bounding logical, Construction.Default Thickness double, Construction.Fascia Depth double, Construction.Maximum Ridge Height double, Construction.Rafter Cut char(200), Dimensions.Area double, Dimensions.Thickness double, Dimensions.Volume double, Graphics.Coarse Scale Fill Color integer, Identity Data.Assembly Code char(200), Identity Data.Assembly Description char(200), Phasing.Phase Created char(200), Pset_RoofCommon.IsExternal logical, Pset_RoofCommon.ProjectedArea double, Pset_RoofCommon.Reference char(200), Pset_RoofCommon.TotalArea double, Pset_ManufacturerTypeInformation.Manufacturer char(200), Pset_ManufacturerTypeInformation.ModelLabel char(200),
      Pset_ManufacturerTypeInformation.ModelReference char(200), Pset_ManufacturerTypeInformation.ProductionYear char(200)
    -> IFC2CityGML_Geometryconverter_parts_roof [GeometryPartExtractor_2_Input]
IFC2CityGML_Geometryconverter_parts_roof
    -> NormalVectorFinder_roof [CoordinateExtractor_Input]
NormalVectorFinder_roof
    NormVec_Output -> TestFilter_6
Note: Keeping main roof
TestFilter_6
    DEFAULT_VALUE = <UNFILTERED>
    TEST_LIST = BOOL_OP,OR,COMPOSITE_TEST,<Unused>,TEST_CLAUSE,"TEST @Value(element_id) = 0_8ahBh7985Rq0OHgF4Iip",mainRoof
    mainRoof -> TestFilter_2
Note: Keeping only uplooking surfaces
TestFilter_2
    DEFAULT_VALUE = <UNFILTERED>
    TEST_LIST = BOOL_OP,OR,COMPOSITE_TEST,<Unused>,TEST_CLAUSE,"TEST @Value(_vz) > 0",upLooking
    upLooking -> AreaCalculator_3
PythonCaller_meanRoofHeight
    NEW_ATTRIBUTES = meanHeight
    PYTHONSOURCE:
      import fme
      import fmeobjects

      # Template Class Interface:
      # When using this class, make sure its name is set as the value of
      # the 'Class or Function to Process Features' transformer parameter
      class FeatureProcessor(object):
          def __init__(self):
              self.fl = []
              self.high = -9999 # For highest point on roof (roof ridge)

          def input(self,feature):
              self.fl.append(feature)
              if float(feature.getAttribute('_max_z_roof')) > self.high:
                  self.high = float(feature.getAttribute('_max_z_roof'))

          def close(self):
              eaveHigh = 9999 # Finding highest eave
              for f in self.fl:
                  # Considered as highest roof if less than 100 mm below
                  if float(f.getAttribute('_max_z_roof')) - self.high < 100:
                      if float(f.getAttribute('_min_z_roof')) < eaveHigh:
                          eaveHigh = float(f.getAttribute('_min_z_roof'))

              nf = fmeobjects.FMEFeature()
              nf.setAttribute('meanHeight', (self.high + eaveHigh)/2.0)
              self.pyoutput(nf)
    PYTHONSYMBOL = FeatureProcessor
    -> AttributeKeeper_meanHeight
AttributeKeeper_meanHeight
    KEEP_ATTRS = meanHeight
    -> Aggregator_5
Wall (reader REVIT_1)
    attributes: element_parent_id char(200), element_id char(200), GlobalId char(200), Name char(200), ObjectType char(200), Tag char(200), Analytical Properties.Roughness double, Analytical Properties.Absorptance double, BaseQuantities.GrossFootprintArea double, BaseQuantities.GrossSideArea double, BaseQuantities.GrossVolume double, BaseQuantities.Height double, BaseQuantities.Length double, BaseQuantities.Width double, Constraints.Base Constraint char(200), Constraints.Base Extension Distance double, Constraints.Base is Attached logical, Constraints.Base Offset double, Constraints.Location Line char(200), Constraints.Related to Mass logical, Constraints.Room Bounding logical, Constraints.Top Constraint char(200), Constraints.Top Extension Distance double, Constraints.Top is Attached logical, Constraints.Top Offset double, Constraints.Unconnected Height double, Construction.Function char(200), Construction.Width double, Construction.Wrapping at Ends char(200), Construction.Wrapping at Inserts char(200),
      Dimensions.Area double, Dimensions.Length double, Dimensions.Volume double, Graphics.Coarse Scale Fill Color integer, Graphics.Coarse Scale Fill Pattern char(200), Identity Data.Assembly Code char(200), Identity Data.Assembly Description char(200), Materials and Finishes.Structural Material char(200), Phasing.Phase Created char(200), Pset_WallCommon.ExtendToStructure logical, Pset_WallCommon.IsExternal logical, Pset_WallCommon.LoadBearing logical, Pset_WallCommon.Reference char(200), Structural.Enable Analytical Model logical, Structural.Structural logical, Structural.Structural Usage char(200), Pset_ManufacturerTypeInformation.Manufacturer char(200), Pset_ManufacturerTypeInformation.ModelLabel char(200), Pset_ManufacturerTypeInformation.ModelReference char(200), Pset_ManufacturerTypeInformation.ProductionYear char(200)
    -> TestFilter_4
TestFilter_4
    DEFAULT_VALUE = <UNFILTERED>
    TEST_LIST = BOOL_OP,OR,COMPOSITE_TEST,<Unused>,TEST_CLAUSE,"TEST @Value(element_parent_id) = 1BPoev16DCuANNTvAOBvAl",basement,BOOL_OP,OR,COMPOSITE_TEST,<Unused>,TEST_CLAUSE,"TEST @Value(element_parent_id) = 1BPoev16DCuANNTvAOBxQP",groundFloor,BOOL_OP,OR,COMPOSITE_TEST,<Unused>,TEST_CLAUSE,"TEST @Value(element_parent_id) = 1BPoev16DCuANNTvAOBxQ8",level2,BOOL_OP,OR,COMPOSITE_TEST,<Unused>,TEST_CLAUSE,"TEST @Value(element_parent_id) = 1BPoev16DCuANNTvAODHS5",level3
    basement -> TestFilter_basement
    groundFloor -> TestFilter_groundFloor
    level2 -> TestFilter_level_2
    level3 -> TestFilter_level_3
Aggregator_2
    SEP = ,
    MODE = Geometry - Assemble One Level
    ORDERED = No
    ID_SELECTION = ID and Parent ID
    ATTR_TO_TRAIT = Yes
    PRESERVE_ID = No
    ACCUM_ATTRS_NAME = Use Attributes From One Feature
    AGGREGATE_TYPE = Homogeneous Collection (If Possible)
    AGGREGATE -> HullReplacer
HullReplacer
    3DMODE_PARAM = 2D
    HULLTYPE_PARAM = Convex ()
    HULL -> Aggregator
Offsetter
    XOFF = 0
    ZOFF = @Value(_min_z_steps)
    MODE = Cartesian Coordinate
    YOFF = 0
    OFFSET -> Aggregator_5
    <REJECTED> -> Offsetter__Rejected_
Aggregator_5
    SEP = ,
    MODE = Geometry - Assemble One Level
    ORDERED = No
    ACCUM_ATTRS_NAME = Merge Incoming Attributes
    AGGREGATE_TYPE = Homogeneous Collection (If Possible)
    AGGREGATE -> Extruder
Extruder
    EXTRUSION_Y = 0.0
    EXTRUSION_X = 0.0
    DIRECTION = Specified
    EXTRUSION_Z = @Value(meanHeight)-@Value(_min_z_steps)
    EXTRUDED -> GeometryExtractor
GeometryExtractor
    ATTR = _geometry
    OMIT_NAMESPACES_DISPLAY = No
    OGC_WKT_PRECISION_DISPLAY = Shortened 64-bit
    REMOVE_GEOMETRY = No
    KIND_LONG = GML v3.1.1
    PREFER_POLYGON_OVER_SURFACE = No
    OGCVERSION = 1.2
    OGEOSMS_URL_PREFIX = http://maps.google.com/?q=
    -> NewFeatureType (writer GML_1)
    -> GeometryExtractor_Output
NewFeatureType (writer GML_1)
GeometryExtractor_Output: Inspector
Offsetter__Rejected_: Inspector

Bookmark: Finding ground level as lowest point of front steps
Note: Using front steps to find ground level. / Not obvious where ground is and seems to be on a sligth slope.
TestFilter_3
    DEFAULT_VALUE = <UNFILTERED>
    TEST_LIST = "BOOL_OP,OR,COMPOSITE_TEST,""""""<Unused>"""""",TEST_CLAUSE,TEST @Value(element_parent_id) = 0yDteS9MPDjesQlw7dC4uU",frontSteps
    frontSteps -> CoordinateExtractor_3
CoordinateExtractor_3
    LIST_NAME = _indices_steps
    MODE = All Coordinates
    -> ListRangeExtractor_3
ListRangeExtractor_3
    MIN = _min_z_steps
    MAX = _max_z_steps
    SRC_LIST = _indices_steps{}.z
    -> GeometryRemover

Bookmark: Prepare to aggregate with footprint
  Only need to pass ground level to offset the footprint elevation. Removing others here.
GeometryRemover
    -> AttributeKeeper
AttributeKeeper
    KEEP_ATTRS = _min_z_steps
    -> Junction

Bookmark: To get ground level
  Aggregating to get ground level as the lowest level of the front steps.
Note: AttributeKeeper : Output
Junction_2
    -> Aggregator
Aggregator
    SEP = ,
    MODE = Geometry - Assemble One Level
    ORDERED = No
    ACCUM_ATTRS_NAME = Merge Incoming Attributes
    AGGREGATE_TYPE = Homogeneous Collection (If Possible)
    AGGREGATE -> Offsetter

Bookmark: Filter out small parts
  Filter out small parts around the chimneys that are uplooking and would be included in one of the roof surfaces even if they are "holes" and not surfaces.
AreaCalculator_3
    AREA_TYPE = Plane Area
    MULT = 1
    AREA_ATTR = _area_roof_up
    -> Tester_2
Tester_2
    TEST_MODE = Automatic
    TEST_CLAUSE = TEST @Value(_area_roof_up) > 0.1
    TEST_DESCRIPTION = ""
    BOOL_OP = OR
    PASSED -> TestFilter_5

Bookmark: To split main roof into two sides
TestFilter_5
    DEFAULT_VALUE = <UNFILTERED>
    TEST_LIST = BOOL_OP,OR,COMPOSITE_TEST,<Unused>,TEST_CLAUSE,"TEST @Value(_vx) > 0",posNormX
    posNormX -> Aggregator_3
    <UNFILTERED> -> Aggregator_4
Aggregator_3
    SEP = ,
    MODE = Geometry - Assemble One Level
    ORDERED = No
    GROUP_BY = element_id
    ACCUM_ATTRS_NAME = Use Attributes From One Feature
    AGGREGATE_TYPE = Homogeneous Collection (If Possible)
    AGGREGATE -> HullReplacer_3
HullReplacer_3
    3DMODE_PARAM = Automatic
    HULLTYPE_PARAM = Convex ()
    HULL -> CoordinateExtractor
Aggregator_4
    SEP = ,
    MODE = Geometry - Assemble One Level
    ORDERED = No
    GROUP_BY = element_id
    ACCUM_ATTRS_NAME = Use Attributes From One Feature
    AGGREGATE_TYPE = Homogeneous Collection (If Possible)
    AGGREGATE -> HullReplacer_2
HullReplacer_2
    3DMODE_PARAM = Automatic
    HULLTYPE_PARAM = Convex ()
    HULL -> CoordinateExtractor_2

Bookmark: Getting max and min z-values
CoordinateExtractor
    LIST_NAME = _indices
    MODE = All Coordinates
    -> ListRangeExtractor
ListRangeExtractor
    MIN = _min_z_roof
    MAX = _max_z_roof
    SRC_LIST = _indices{}.z
    -> PythonCaller_meanRoofHeight
CoordinateExtractor_2
    LIST_NAME = _indices
    MODE = All Coordinates
    -> ListRangeExtractor_2
ListRangeExtractor_2
    MIN = _min_z_roof
    MAX = _max_z_roof
    SRC_LIST = _indices{}.z
    -> PythonCaller_meanRoofHeight

Bookmark: Keeping external walls only
TestFilter_basement
    DEFAULT_VALUE = <UNFILTERED>
    TEST_LIST = BOOL_OP,OR,COMPOSITE_TEST,<Unused>,TEST_CLAUSE,"TEST @Value(Pset_WallCommon.IsExternal) = Yes",External
TestFilter_groundFloor
    DEFAULT_VALUE = <UNFILTERED>
    TEST_LIST = BOOL_OP,OR,COMPOSITE_TEST,<Unused>,TEST_CLAUSE,"TEST @Value(Pset_WallCommon.IsExternal) = Yes",External
    External -> Aggregator_2
TestFilter_level_2
    DEFAULT_VALUE = <UNFILTERED>
    TEST_LIST = BOOL_OP,OR,COMPOSITE_TEST,<Unused>,TEST_CLAUSE,"TEST @Value(Pset_WallCommon.IsExternal) = Yes",External
TestFilter_level_3
    DEFAULT_VALUE = <UNFILTERED>
    TEST_LIST = BOOL_OP,OR,COMPOSITE_TEST,<Unused>,TEST_CLAUSE,"TEST @Value(Pset_WallCommon.IsExternal) = Yes",External

FME custom transformer IFC2CityGML_Geometryconverter_parts

GeometryPartExtractor_2_Input (input)
    -> GeometryPartExtractor_2
Note: Check that geometry name is solid
GeometryPartExtractor_2
    EXTRACTTYPE_PARAM = Extract
    GQUERY:
      for $geom in //geometry
      where $geom/@fme_geometry_name = 'Body'
      return number($geom/@fme_id)
    PROCESSED -> GeometryCoercer_2
    UNTOUCHED -> GeometryCoercer_2
Note: Check for geometry type IFMEExtrusion OR IFMEBRepSolid
GeometryCoercer_2
    KIND = fme_composite_surface
    GQUERY:
      for $geom in //geometry
      where $geom/@fme_geometry_type = 'IFMEExtrusion'
      or $geom/@fme_geometry_type = 'IFMEBRepSolid'
      return number($geom/@fme_id)
    COERCED -> Deaggregator
    UNTOUCHED -> Deaggregator
Note: Changed split compostites to YES
Deaggregator
    SPLIT_COMPOSITES = Yes
    EXPLODE_INSTANCES = No
    LIST_ATTR_MODE_LOOKUP = LEAN
    GEOM_NAME_FIELD = _geometry_name
    MODE = Flatten All Levels
    DEAGGREGATED -> GeometryRefiner
Note: Keep this or not?
GeometryRefiner
    -> Output (output)
Output (output)

FME custom transformer NormalVectorFinder

CoordinateExtractor_Input (input)
    -> CoordinateCounter
Note: Note that there are wall surfaces (beloning to "Takplan" in KTH where index 0 is in a vertical line with both first and second last index ont eh line i.e. the normals arr not correct.
NormVec_Output (output)

Bookmark: Calculate Normal Vector (_vx, _vy, _vz)
  There was a special case with one outer wall surface (see notes) which gave wrong orientation due to concave shape. This version is using coordinates with index 0, 1, (nbr coords -4) to test if that solves the problem. See notes for more details.
Note: Need to know the number of / coordinates to find the second / last.
CoordinateCounter
    CNT_ATTR = _coordcount_normal_vector
    -> CoordinateExtractor_7
CoordinateExtractor_7
    Z_ATTR = _z0
    Y_ATTR = _y0
    X_ATTR = _x0
    Z_DEFAULT = -9999
    IND = 0
    -> CoordinateExtractor_8
CoordinateExtractor_8
    Z_ATTR = _z1
    Y_ATTR = _y1
    X_ATTR = _x1
    Z_DEFAULT = -9999
    IND = 1
    -> CoordinateExtractor_9
CoordinateExtractor_9
    Z_ATTR = _z2
    Y_ATTR = _y2
    X_ATTR = _x2
    Z_DEFAULT = -9999
    IND = @Value(_coordcount_normal_vector)-2
    -> AttributeCreator_5
AttributeCreator_5
    ATTR_LIST = _vx0,@Evaluate(@Value(_x1)-@Value(_x0)),_vy0,@Evaluate(@Value(_y1)-@Value(_y0)),_vz0,@Evaluate(@Value(_z1)-@Value(_z0)),_vx1,@Evaluate(@Value(_x2)-@Value(_x0)),_vy1,@Evaluate(@Value(_y2)-@Value(_y0)),_vz1,@Evaluate(@Value(_z2)-@Value(_z0))
    -> AttributeCreator_6
AttributeCreator_6
    ATTR_LIST = _vx,@Evaluate(@Value(_vy0)*@Value(_vz1)-@Value(_vz0)*@Value(_vy1)),_vy,@Evaluate(@Value(_vz0)*@Value(_vx1)-@Value(_vx0)*@Value(_vz1)),_vz,@Evaluate(@Value(_vx0)*@Value(_vy1)-@Value(_vy0)*@Value(_vx1))
    -> AttributeRemover
AttributeRemover
    REMOVE_ATTRS = _coordcount_normal_vector
    -> NormVec_Output (output)

Bookmark: Calculate Normal Vector (_vx, _vy, _vz)
CoordinateExtractor
    Z_ATTR = _z0
    Y_ATTR = _y0
    X_ATTR = _x0
    Z_DEFAULT = -9999
    IND = 0
    -> CoordinateExtractor_2
CoordinateExtractor_2
    Z_ATTR = _z1
    Y_ATTR = _y1
    X_ATTR = _x1
    Z_DEFAULT = -9999
    IND = 1
    -> CoordinateExtractor_3
CoordinateExtractor_3
    Z_ATTR = _z2
    Y_ATTR = _y2
    X_ATTR = _x2
    Z_DEFAULT = -9999
    IND = 3
    -> AttributeCreator
AttributeCreator
    ATTR_LIST = _vx0,@Evaluate(@Value(_x1)-@Value(_x0)),_vy0,@Evaluate(@Value(_y1)-@Value(_y0)),_vz0,@Evaluate(@Value(_z1)-@Value(_z0)),_vx1,@Evaluate(@Value(_x2)-@Value(_x0)),_vy1,@Evaluate(@Value(_y2)-@Value(_y0)),_vz1,@Evaluate(@Value(_z2)-@Value(_z0))
    -> AttributeCreator_2
AttributeCreator_2
    ATTR_LIST = _vx,@Evaluate(@Value(_vy0)*@Value(_vz1)-@Value(_vz0)*@Value(_vy1)),_vy,@Evaluate(@Value(_vz0)*@Value(_vx1)-@Value(_vx0)*@Value(_vz1)),_vz,@Evaluate(@Value(_vx0)*@Value(_vy1)-@Value(_vy0)*@Value(_vx1))

FME workspace revit2undervisningshuset.fmw
Title: revit2undervisningshuset

Parameters:
- SourceDataset_REVIT = D:\Temp\A-40-V-0000-RelationNoHexOrg_Adjusted.ifc   # Source Revit Export File(s)
- DestDataset_GML = D:\Testbed\Jings_project\Undervisningshuset\Uhuset_LOD23.gml   # Destination Geography Markup Language (GML) File
- SourceDataset_GEOTIFF = D:\Temp\hojd2m3006_6583032_674382.tif   # Source GeoTIFF File(s)

Readers:
- REVIT_1: REVIT from $(SourceDataset_REVIT)
- GEOTIFF_1: GEOTIFF from $(SourceDataset_GEOTIFF)

Writers:
- GML_1: GML to $(DestDataset_GML)
- GML_2: GML to $(DestDataset_GML)

BuildingColumn (reader REVIT_1)
    attributes: element_parent_id char(200), element_id char(200), GlobalId char(200), Name char(200), ObjectType char(200), Tag char(200), BaseQuantities.CrossSectionArea double, BaseQuantities.GrossVolume double, BaseQuantities.Length double, BaseQuantities.OuterSurfaceArea double, Constraints.Base Level char(200), Constraints.Base Offset double, Constraints.Moves With Grids logical, Constraints.Room Bounding logical, Constraints.Top Level char(200), Constraints.Top Offset double, Dimensions.Depth double, Dimensions.Offset Base double, Dimensions.Offset Top double, Dimensions.Width double, Identity Data.Assembly Code char(200), Identity Data.Assembly Description char(200), Identity Data.OmniClass Number char(200), Identity Data.OmniClass Title char(200), Phasing.Phase Created char(200), Pset_ColumnCommon.IsExternal logical, Pset_ColumnCommon.LoadBearing logical, Pset_ColumnCommon.Reference char(200), Pset_ColumnCommon.Slope double, Pset_ManufacturerTypeInformation.Manufacturer char(200),
      Pset_ManufacturerTypeInformation.ModelLabel char(200), Pset_ManufacturerTypeInformation.ModelReference char(200), Pset_ManufacturerTypeInformation.ProductionYear char(200)
    -> TestFilter_5
Note: Orientor : Oriented
Junction_12
    -> Scaler
BuildingStorey (reader REVIT_1)
    attributes: element_id char(200), element_parent_id char(200), Elevation double, GlobalId char(200), Name char(200), LongName char(200), Dimensions.Computation Height double, Identity Data.Building Story char(200), Identity Data.Structural char(200), Pset_BuildingStoreyCommon.AboveGround char(200)
    -> FeatureMerger_wallsStoreys [SUPPLIER]
Wall (reader REVIT_1)
    attributes: element_parent_id char(200), element_id char(200), GlobalId char(200), Name char(200), ObjectType char(200), Tag char(200), Analytical Properties.Roughness double, Analytical Properties.Absorptance double, BaseQuantities.GrossFootprintArea double, BaseQuantities.GrossSideArea double, BaseQuantities.GrossVolume double, BaseQuantities.Height double, BaseQuantities.Length double, BaseQuantities.Width double, Constraints.Base Constraint char(200), Constraints.Base Extension Distance double, Constraints.Base is Attached logical, Constraints.Base Offset double, Constraints.Location Line char(200), Constraints.Related to Mass logical, Constraints.Room Bounding logical, Constraints.Top Constraint char(200), Constraints.Top Extension Distance double, Constraints.Top is Attached logical, Constraints.Top Offset double, Constraints.Unconnected Height double, Construction.Function char(200), Construction.Width double, Construction.Wrapping at Ends char(200), Construction.Wrapping at Inserts char(200),
      Dimensions.Area double, Dimensions.Length double, Dimensions.Volume double, Graphics.Coarse Scale Fill Color integer, Graphics.Coarse Scale Fill Pattern char(200), Identity Data.Assembly Code char(200), Identity Data.Assembly Description char(200), Materials and Finishes.Structural Material char(200), Phasing.Phase Created char(200), Pset_WallCommon.ExtendToStructure logical, Pset_WallCommon.IsExternal logical, Pset_WallCommon.LoadBearing logical, Pset_WallCommon.Reference char(200), Structural.Enable Analytical Model logical, Structural.Structural logical, Structural.Structural Usage char(200), Pset_ManufacturerTypeInformation.Manufacturer char(200), Pset_ManufacturerTypeInformation.ModelLabel char(200), Pset_ManufacturerTypeInformation.ModelReference char(200), Pset_ManufacturerTypeInformation.ProductionYear char(200)
    -> TestFilter_WallsByStorey
Note: AttributeCreator_mergeID_footprint : Output
Junction_6
    -> FeatureMerger [REQUESTOR]
Note: KTH Educational Building (Uhuset) to LOD1 and LOD2 / This workspace is released under the 3-Clause BSD License. For details, see the Description of this workspace. See also https://opensource.org/licenses/BSD-3-Clause / This script reads an IFC model and tranforms it toLOD1 and LOD2.3 CityGML building model geometry (GML 3.1.1). The IFC model is not included with the workbench. / Roof elements are used to extract the footprint of the building and BuildingStorey elements are used to derive the elevation of the building footprint. / For the LOD1 models the height of the building is derived from Roof elements. / To create the LOD2.3 building model the roof surfaces are extruded downwards and clipped at ground level with the building footprint. A terrace on the roof is then clipped from the model by extruding the floor of the terrace (Slab element). Finally, a greenhouse on the terrace is added (BuildingColumn elements) / The workbench also adds a terrain intersection line to the building model by placing the model in a Digital Elevation Model (DEM). / For suggested detailed LOD definitions see: / Biljecki, F., Ledoux, H., Stoter, J., 2016a. An improved LOD specification for 3D building models. Computers, Environment, and Urban Systems, vol. 59, pp. 25-37. https://doi.org/10.3390/ijgi4042842. / The workbench is created with FME version 2017.1.2.1
Roof (reader REVIT_1)
    attributes: element_parent_id char(200), element_id char(200), GlobalId char(200), Name char(200), ObjectType char(200), Tag char(200), Analytical Properties.Absorptance double, Analytical Properties.Roughness double, Constraints.Base Level char(200), Constraints.Base Offset From Level double, Constraints.Cutoff Offset double, Constraints.Related to Mass logical, Constraints.Room Bounding logical, Construction.Default Thickness double, Construction.Fascia Depth double, Construction.Maximum Ridge Height double, Construction.Rafter Cut char(200), Dimensions.Area double, Dimensions.Thickness double, Dimensions.Volume double, Graphics.Coarse Scale Fill Color integer, Identity Data.Assembly Code char(200), Identity Data.Assembly Description char(200), Phasing.Phase Created char(200), Pset_RoofCommon.IsExternal logical, Pset_RoofCommon.ProjectedArea double, Pset_RoofCommon.Reference char(200), Pset_RoofCommon.TotalArea double, Pset_ManufacturerTypeInformation.Manufacturer char(200), Pset_ManufacturerTypeInformation.ModelLabel char(200),
      Pset_ManufacturerTypeInformation.ModelReference char(200), Pset_ManufacturerTypeInformation.ProductionYear char(200)
    -> Solid2surface_3 [GeometryPartExtractor_3_Input]
Solid2surface_3
    GeometryRefiner_2_Output -> normalFinder_3 [CoordinateCounter_2_Input]
normalFinder_3
    AttributeRemover_2_Output -> TestFilter
Note: Filter surfaces by orientation
TestFilter
    TEST_LIST = BOOL_OP,OR,COMPOSITE_TEST,<Unused>,TEST_CLAUSE,"TEST @Value(_vz) > 0",upLooking,BOOL_OP,OR,COMPOSITE_TEST,<Unused>,TEST_CLAUSE,"TEST @Value(_vz) = 0",horizpntal,BOOL_OP,OR,COMPOSITE_TEST,<Unused>,TEST_CLAUSE,"TEST @Value(_vz) < 0",downLooking
    DEFAULT_VALUE = <UNFILTERED>
    upLooking -> AreaCalculator
Aggregator
    AGGREGATE_TYPE = Homogeneous Collection (If Possible)
    ORDERED = No
    ACCUM_ATTRS_NAME = Use Attributes From One Feature
    MODE = Geometry - Assemble One Level
    SEP = ,
    AGGREGATE -> Extruder_LOD2_roofDown
    AGGREGATE -> AttributeCreator_mergeID_LOD2
Note: Extruding from roof and down below ground. / The roof is leaning so it is nto possible to extrude / down to a flat surface along ground.
Extruder_LOD2_roofDown
    EXTRUSION_Y = 0.0
    DIRECTION = Specified
    EXTRUSION_X = 0.0
    EXTRUSION_Z = @Value(_max_z_roof)*-1.0
    EXTRUDED -> Clipper_LOD2 [CLIPPEE]
AttributeCreator_mergeID_LOD2
    ATTR_TABLE = SET_TO mergeID = 1
    -> FeatureMerger [SUPPLIER]
    -> Junction_7
Note: FeatureMerger_2 : Supplier
Junction_7
    -> Junction_8
Note: LOD2 with no roof features
Clipper_LOD2
    LINES_AS_SEGMENTS = No
    BOUNDARY_CASES = Treat as Inside
    VAL_SOURCE = Clippee Only
    CLIP_TYPE = Multiple Clippers
    CLIPPED_ATTR = _clipped
    CREATE_AGGREGATES = Yes
    MEASURE_TYPE = Continuous
    MISSING_VAL_MODE = Compute
    PRESERVE_CLIPPEE_EXTENTS = No
    INSIDE -> Clipper_LOD2.3 [CLIPPEE]
Note: Sorter_2 : Input
Junction
    -> Junction_2
GeometryExtractor_LOD1_Output: Inspector
Slab (reader REVIT_1)
    attributes: element_parent_id char(200), element_id char(200), GlobalId char(200), Name char(200), ObjectType char(200), Tag char(200), OverallHeight double, OverallWidth double, Analytical Properties.Absorptance double, Analytical Properties.Roughness double, BaseQuantities.GrossArea double, BaseQuantities.GrossVolume double, BaseQuantities.Perimeter double, BaseQuantities.Width double, Constraints.Base Level char(200), Constraints.Base Offset From Level double, Constraints.Cutoff Offset double, Constraints.Height Offset From Level double, Constraints.Level char(200), Constraints.Related to Mass logical, Constraints.Room Bounding logical, Construction.Default Thickness double, Construction.Fascia Depth double, Construction.Function char(200), Construction.Maximum Ridge Height double, Construction.Rafter Cut char(200), Construction.Rafter or Truss char(200), Construction.Thickness double, Dimensions.Area double, Dimensions.Perimeter double,
      Dimensions.Slope double, Dimensions.Thickness double, Dimensions.Volume double, Graphics.Coarse Scale Fill Color double, Identity Data.Assembly Code char(200), Identity Data.Assembly Description char(200), Materials and Finishes.Structural Material char(200), Phasing.Phase Created char(200), Pset_RoofCommon.IsExternal logical, Pset_RoofCommon.ProjectedArea double, Pset_RoofCommon.Reference char(200), Pset_RoofCommon.TotalArea double, Pset_SlabCommon.IsExternal logical, Pset_SlabCommon.LoadBearing logical, Pset_SlabCommon.Reference char(200), Pset_ManufacturerTypeInformation.Manufacturer char(200), Pset_ManufacturerTypeInformation.ModelLabel char(200), Pset_ManufacturerTypeInformation.ModelReference char(200), Pset_ManufacturerTypeInformation.ProductionYear char(200)
    -> Tester_roofHole
Note: Extracting the slab inside the / "terrace" on the roof.
Tester_roofHole
    TEST_CLAUSE = TEST @Value(element_id) = 0aM$xFlJv9K9LLMzJ05ahT
    TEST_MODE = Automatic
    BOOL_OP = OR
    PASSED -> Solid2surface_4 [GeometryPartExtractor_3_Input]
Solid2surface_4
    GeometryRefiner_2_Output -> normalFinder_4 [CoordinateCounter_2_Input]
normalFinder_4
    AttributeRemover_2_Output -> TestFilter_2
Note: Filter surfaces by orientation
TestFilter_2
    TEST_LIST = BOOL_OP,OR,COMPOSITE_TEST,<Unused>,TEST_CLAUSE,"TEST @Value(_vz) > 0",upLooking,BOOL_OP,OR,COMPOSITE_TEST,<Unused>,TEST_CLAUSE,"TEST @Value(_vz) = 0",horizpntal,BOOL_OP,OR,COMPOSITE_TEST,<Unused>,TEST_CLAUSE,"TEST @Value(_vz) < 0",downLooking
    DEFAULT_VALUE = <UNFILTERED>
    upLooking -> HullReplacer_3
Note: To clip the terrace
Clipper_LOD2.3
    LINES_AS_SEGMENTS = No
    BOUNDARY_CASES = Treat as Inside
    VAL_SOURCE = Clippee Only
    CLIP_TYPE = Multiple Clippers
    CLIPPED_ATTR = _clipped
    CREATE_AGGREGATES = Yes
    MEASURE_TYPE = Continuous
    MISSING_VAL_MODE = Compute
    PRESERVE_CLIPPEE_EXTENTS = No
    OUTSIDE -> Scaler
Scaler
    YSCALE = 0.001
    SCALE_ORIGIN = 0,0
    XSCALE = 0.001
    RASTER_SCALING = Extents
    TEXT_LOC_ONLY = Location and Size
    ZSCALE = 0.001
    SCALED -> GeometryExtractor_LOD23
Note: To get GML 3.1.1 geometry
GeometryExtractor_LOD23
    OGC_WKT_PRECISION_DISPLAY = Shortened 64-bit
    OGCVERSION = 1.2
    KIND_LONG = GML v3.1.1
    OMIT_NAMESPACES_DISPLAY = No
    ATTR = _geometry
    OGEOSMS_URL_PREFIX = http://maps.google.com/?q=
    PREFER_POLYGON_OVER_SURFACE = No
    REMOVE_GEOMETRY = No
    -> Offsetter_LOD2
Note: Offsetting model to "place" it / in the DEM used to extract the / terrain intersection line.
Offsetter_LOD2
    MODE = Cartesian Coordinate
    YOFF = 6583130
    ZOFF = -2
    XOFF = 674500
    OFFSET -> U_huset_LOD23 (writer GML_1)
    OFFSET -> Junction_9
    OFFSET -> Offsetter_LOD2_Offset
Offsetter_LOD2_Offset: Inspector
Note: In case a terrain intersection line is added.
Note: Clipper : Clipper
Junction_9
    -> Junction_10
U_huset_LOD23 (writer GML_1)

Bookmark: To create solid of the greenhouse on the terrace
TestFilter_5
    TEST_LIST = BOOL_OP,OR,COMPOSITE_TEST,<Unused>,TEST_CLAUSE,"TEST @Value(element_id) = 1VgTXJPObCauuaJRT71SGg",greenHouse
    DEFAULT_VALUE = <UNFILTERED>
    greenHouse -> Solid2surface_2 [GeometryPartExtractor_3_Input]
    greenHouse -> CoordinateExtractor_6
CoordinateExtractor_6
    MODE = All Coordinates
    LIST_NAME = _indices_gh
    -> ListRangeExtractor_2
ListRangeExtractor_2
    SRC_LIST = _indices_gh{}.z
    MIN = _min_z_gh
    MAX = _max_z_gh
    -> GeometryRemover
GeometryRemover
    -> AttributeKeeper_3
AttributeKeeper_3
    KEEP_ATTRS = _max_z_gh,_min_z_gh
    -> Aggregator_6
Solid2surface_2
    GeometryRefiner_2_Output -> normalFinder_2 [CoordinateCounter_2_Input]
normalFinder_2
    AttributeRemover_2_Output -> TestFilter_6
TestFilter_6
    TEST_LIST = BOOL_OP,OR,COMPOSITE_TEST,<Unused>,TEST_CLAUSE,"TEST @Value(_vz) > 0",uplooking
    DEFAULT_VALUE = <UNFILTERED>
    uplooking -> AreaCalculator_2
AreaCalculator_2
    MULT = 1
    AREA_ATTR = _area_gh
    AREA_TYPE = Plane Area
    -> Sorter_3
Sorter_3
    SORT_PARM = _area_gh NUMERIC DESCENDING
    SORTED -> Counter_4
Counter_4
    DOMAIN = counter
    SCOPE = Local
    CNT_ATTR = _count_gh
    START = 0
    -> Tester_3
Tester_3
    TEST_CLAUSE = TEST @Value(_count_gh) <= 4
    TEST_DESCRIPTION = ""
    TEST_MODE = Automatic
    BOOL_OP = OR
    PASSED -> Tester_4
Tester_4
    TEST_CLAUSE = TEST @Value(_vx) < 0
    TEST_DESCRIPTION = ""
    TEST_MODE = Automatic
    BOOL_OP = OR
    PASSED -> HullAccumulator
    FAILED -> HullAccumulator_2
HullAccumulator
    HULLTYPE_PARAM = Convex ()
    DEFAULTZ = 0
    3DMODE_PARAM = 3D
    HULL -> Aggregator_5
HullAccumulator_2
    HULLTYPE_PARAM = Convex ()
    DEFAULTZ = 0
    3DMODE_PARAM = 3D
    HULL -> Aggregator_5
Aggregator_5
    ID_SELECTION = ID and Parent ID
    AGGREGATE_TYPE = Homogeneous Collection (If Possible)
    ORDERED = No
    ACCUM_ATTRS_NAME = Use Attributes From One Feature
    MODE = Geometry - Assemble One Level
    SEP = ,
    PRESERVE_ID = No
    ATTR_TO_TRAIT = Yes
    AGGREGATE -> Aggregator_6
Aggregator_6
    AGGREGATE_TYPE = Homogeneous Collection (If Possible)
    ORDERED = No
    ACCUM_ATTRS_NAME = Merge Incoming Attributes
    MODE = Geometry - Assemble One Level
    SEP = ,
    AGGREGATE -> Extruder_4
Extruder_4
    EXTRUSION_Y = 0.0
    DIRECTION = Specified
    EXTRUSION_X = 0.0
    EXTRUSION_Z = -(@Value(_max_z_gh)-@Value(_min_z_gh)+100)
    EXTRUDED -> Orientor
Orientor
    FLIP_APPEARANCES_CHOICE = Yes
    KIND = REVERSE
    ORIENTED -> Junction_11
Note: Merging with "the rest" of the building.
Note: Scaler : Input
Junction_11
    -> Junction_12

Bookmark: Creating footprint of building and offsetting to ground level
  Elevation taken from building storey
TestFilter_WallsByStorey
    TEST_LIST = BOOL_OP,OR,COMPOSITE_TEST,<Unused>,TEST_CLAUSE,"TEST @Value(element_parent_id) = 1snBVg$Wf5gOKU1iNPpeLV",Plan_1,BOOL_OP,OR,COMPOSITE_TEST,<Unused>,TEST_CLAUSE,"TEST @Value(element_parent_id) = 1snBVg$Wf5gOKU1iNPpNEm",Plan_2,BOOL_OP,OR,COMPOSITE_TEST,<Unused>,TEST_CLAUSE,"TEST @Value(element_parent_id) = 1snBVg$Wf5gOKU1iNPox5E",Plan_3,BOOL_OP,OR,COMPOSITE_TEST,<Unused>,TEST_CLAUSE,"TEST @Value(element_parent_id) = 1snBVg$Wf5gOKU1iNPox55",Plan_4,BOOL_OP,OR,COMPOSITE_TEST,<Unused>,TEST_CLAUSE,"TEST @Value(element_parent_id) = 1snBVg$Wf5gOKU1iNPox5S",Plan_5,BOOL_OP,OR,COMPOSITE_TEST,<Unused>,TEST_CLAUSE,"TEST @Value(element_parent_id) = 1snBVg$Wf5gOKU1iNPox5J",Plan_6,BOOL_OP,OR,COMPOSITE_TEST,<Unused>,TEST_CLAUSE,"TEST @Value(element_parent_id) = 1snBVg$Wf5gOKU1iNPox4g",Plan_7,BOOL_OP,OR,COMPOSITE_TEST,<Unused>,TEST_CLAUSE,"TEST @Value(element_parent_id) = 1snBVg$Wf5gOKU1iNPox4X",Takplan,BOOL_OP,OR,COMPOSITE_TEST,<Unused>,TEST_CLAUSE,"TEST @Value(element_parent_id) = 1snBVg$Wf5gOKU1iNPox4p",Taknock
    DEFAULT_VALUE = <UNFILTERED>
    Plan_2 -> FeatureMerger_wallsStoreys [REQUESTOR]
    Plan_3 -> Aggregator_2
FeatureMerger_wallsStoreys
    PROCESS_DUPS = No
    SUPPLIERS_FIRST = No
    ATTR_ACCUM_MODE = Merge Supplier
    ATTR_CONFLICT_RES = Use Requestor
    IGNORE_NULLS = No
    MERGE_TYPE = Attributes Only
    JOIN_KEYS = @Value(element_parent_id) @Value(element_id) AUTO
    REJECT_NULL_MISSING_KEYS = No
    MERGED -> Aggregator_3
Aggregator_3
    AGGREGATE_TYPE = Homogeneous Collection (If Possible)
    ORDERED = No
    ACCUM_ATTRS_NAME = Use Attributes From One Feature
    MODE = Geometry - Assemble One Level
    SEP = ,
    AGGREGATE -> Aggregator_4
Aggregator_2
    ID_SELECTION = ID and Parent ID
    AGGREGATE_TYPE = Homogeneous Collection (If Possible)
    ORDERED = No
    ACCUM_ATTRS_NAME = Use Attributes From One Feature
    MODE = Geometry - Assemble One Level
    SEP = ,
    PRESERVE_ID = No
    ATTR_TO_TRAIT = Yes
    AGGREGATE -> Aggregator_4
Aggregator_4
    AGGREGATE_TYPE = Homogeneous Collection (If Possible)
    ORDERED = No
    ACCUM_ATTRS_NAME = Merge Incoming Attributes
    MODE = Geometry - Assemble One Level
    SEP = ,
    AGGREGATE -> HullReplacer_2
HullReplacer_2
    HULLTYPE_PARAM = Convex ()
    3DMODE_PARAM = Automatic
    HULL -> SurfaceFootprintReplacer
SurfaceFootprintReplacer
    LIGHT_Z = 1
    LIGHT_Y = 0
    LIGHT_X = 0
    SHADOW_MODE = Overhead Shadow
    OFFSET_Z = 0
    FOOTPRINT -> Offsetter_footprint2ground
Offsetter_footprint2ground
    MODE = Cartesian Coordinate
    YOFF = 0
    ZOFF = @Value(Elevation)
    XOFF = 0
    OFFSET -> AttributeKeeper_footprint2ground
AttributeKeeper_footprint2ground
    KEEP_ATTRS = Elevation
    -> AttributeCreator_mergeID_footprint
AttributeCreator_mergeID_footprint
    ATTR_TABLE = SET_TO mergeID = 1
    -> Junction_3
    -> Junction_5
Note: For LOD2: / FeatureMerger : Requestor
Junction_5
    -> Junction_6
Note: For LOD1: / FeatureMerger_footprint_meanHeight : Requestor
Junction_3
    -> Junction_4

Bookmark: LOD1
Note: AttributeCreator_mergeID_footprint : Output
Junction_4
    -> FeatureMerger_footprint_meanHeight [REQUESTOR]
Note: ListRangeExtractor : Output
Junction_2
    -> Sorter_2
AttributeCreator_mergeID_meanHeight
    ATTR_TABLE = SET_TO mergeID = 1
    -> FeatureMerger_footprint_meanHeight [SUPPLIER]
FeatureMerger_footprint_meanHeight
    PROCESS_DUPS = No
    SUPPLIERS_FIRST = No
    ATTR_ACCUM_MODE = Merge Supplier
    ATTR_CONFLICT_RES = Use Requestor
    IGNORE_NULLS = No
    MERGE_TYPE = Attributes Only
    JOIN_KEYS = @Value(mergeID) @Value(mergeID) AUTO
    REJECT_NULL_MISSING_KEYS = No
    MERGED -> Extruder
Extruder
    EXTRUSION_Y = 0.0
    DIRECTION = Specified
    EXTRUSION_X = 0.0
    EXTRUSION_Z = @Value(_meanRoofHeight)-@Value(Elevation)
    EXTRUDED -> Scaler_2
Scaler_2
    YSCALE = 0.001
    SCALE_ORIGIN = 0,0
    XSCALE = 0.001
    RASTER_SCALING = Extents
    TEXT_LOC_ONLY = Location and Size
    ZSCALE = 0.001
    SCALED -> GeometryExtractor_LOD1
GeometryExtractor_LOD1
    OGC_WKT_PRECISION_DISPLAY = Shortened 64-bit
    OGCVERSION = 1.2
    KIND_LONG = GML v3.1.1
    OMIT_NAMESPACES_DISPLAY = No
    ATTR = _geometry
    OGEOSMS_URL_PREFIX = http://maps.google.com/?q=
    PREFER_POLYGON_OVER_SURFACE = No
    REMOVE_GEOMETRY = No
    -> NewFeatureType (writer GML_2)
    -> GeometryExtractor_LOD1_Output
NewFeatureType (writer GML_2)

Bookmark: Getting the two largest uplooking surfaces
AreaCalculator
    MULT = 1
    AREA_ATTR = _area_roofSurface
    AREA_TYPE = Plane Area
    -> Sorter
Sorter
    SORT_PARM = _area_roofSurface NUMERIC DESCENDING
    SORTED -> Counter
Counter
    DOMAIN = counter
    SCOPE = Local
    CNT_ATTR = _count_roofArea
    START = 0
    -> Tester
Tester
    TEST_CLAUSE = TEST @Value(_count_roofArea) < 2
    TEST_MODE = Automatic
    BOOL_OP = OR
    PASSED -> HullReplacer
    FAILED -> Tester_Failed
Tester_Failed: Inspector [off]

Bookmark: Preparing for extrusion
  To remove holes and getting max and min z-ccordinates of the roof surfaces.
HullReplacer
    HULLTYPE_PARAM = Convex ()
    3DMODE_PARAM = Automatic
    HULL -> CoordinateExtractor
CoordinateExtractor
    MODE = All Coordinates
    IND = 0
    Y_ATTR = _y
    X_ATTR = _x
    LIST_NAME = _indices
    Z_ATTR = _z
    -> ListRangeExtractor
ListRangeExtractor
    SRC_LIST = _indices{}.z
    MIN = _min_z_roof
    MAX = _max_z_roof
    -> Junction
    -> Aggregator

Bookmark: Solid for clipping the terrace on the roof
  Creates a solid starting at the floor of the terrace and extending over the highest part of the roof. Used to clip out the terrace to create a more detailed LOD2 model.
Note: AttributeCreator_mergeID_LOD2 : Output
Junction_8
    -> FeatureMerger_2 [SUPPLIER]
HullReplacer_3
    HULLTYPE_PARAM = Convex ()
    3DMODE_PARAM = Automatic
    HULL -> AttributeCreator_mergeID_LOD2_2
AttributeCreator_mergeID_LOD2_2
    ATTR_TABLE = SET_TO mergeID = 1
    -> FeatureMerger_2 [REQUESTOR]
FeatureMerger_2
    PROCESS_DUPS = No
    SUPPLIERS_FIRST = No
    ATTR_ACCUM_MODE = Merge Supplier
    ATTR_CONFLICT_RES = Use Requestor
    IGNORE_NULLS = No
    MERGE_TYPE = Attributes Only
    JOIN_KEYS = @Value(mergeID) @Value(mergeID) AUTO
    REJECT_NULL_MISSING_KEYS = No
    MERGED -> Extruder_2
Extruder_2
    EXTRUSION_Y = 0.0
    DIRECTION = Specified
    EXTRUSION_X = 0.0
    EXTRUSION_Z = @Value(_max_z_roof)
    EXTRUDED -> Clipper_LOD2.3 [CLIPPER]

Bookmark: To clip the model at gound level
  Creating a solid with the base at ground elevation and extending over the roof. Used to clip the solid that starts fromt eroof and extends below groound. The leaning roof does nto allow an extrusion to ground level directly.
FeatureMerger
    PROCESS_DUPS = No
    SUPPLIERS_FIRST = No
    ATTR_ACCUM_MODE = Merge Supplier
    ATTR_CONFLICT_RES = Use Requestor
    IGNORE_NULLS = No
    MERGE_TYPE = Attributes Only
    JOIN_KEYS = @Value(mergeID) @Value(mergeID) AUTO
    REJECT_NULL_MISSING_KEYS = No
    MERGED -> Bufferer
Note: Make sure it is larger than / the solid to clip
Bufferer
    CAP_STYLE = Round
    CORNER_STYLE = Round
    OFFSET = 1000
    ANGLE = 22.5
    BUFFERED -> Offsetter
Offsetter
    MODE = Cartesian Coordinate
    YOFF = 0
    ZOFF = @Value(Elevation)
    XOFF = 0
    OFFSET -> Extruder_LOD2_groundUp
Extruder_LOD2_groundUp
    EXTRUSION_Y = 0.0
    DIRECTION = Specified
    EXTRUSION_X = 0.0
    EXTRUSION_Z = @Value(_max_z_roof)
    EXTRUDED -> Clipper_LOD2 [CLIPPER]

Bookmark: Find the roof section to base mean height on
  Mean height is derived from the roof ridge and the lower part of the roof section that is highest.
Sorter_2
    SORT_PARM = _min_z_roof NUMERIC DESCENDING
    SORTED -> Counter_2
Counter_2
    DOMAIN = counter
    SCOPE = Local
    CNT_ATTR = _count_roof_z_min
    START = 0
    -> Tester_2
Tester_2
    TEST_CLAUSE = TEST @Value(_count_roof_z_min) = 0
    TEST_MODE = Automatic
    BOOL_OP = OR
    PASSED -> AttributeCreator_meanHeight
AttributeCreator_meanHeight
    ATTR_TABLE = SET_TO _meanRoofHeight = @Evaluate((@Value(_max_z_roof)+@Value(_min_z_roof))/2.0)
    -> AttributeCreator_mergeID_meanHeight

Bookmark: Creating terrain intersection line for the model
Note: Offsetter_2 : Offset
Junction_10
    -> Clipper [CLIPPER]
GEOTIFF (reader GEOTIFF_1)
    -> RasterCellCoercer
RasterCellCoercer
    PRESERVE_ATTRIBUTES = No
    EXTRACT_NODATA = No
    EXTRACT_BAND_VALUES_AS = Z Values
    CELL_GEOMETRY = Points
    -> TINGenerator [POINTS/LINES]
TINGenerator
    TOLERANCE = 1
    TRIANGLES -> Extruder_3
Extruder_3
    EXTRUSION_Y = 0.0
    DIRECTION = Specified
    EXTRUSION_X = 0.0
    EXTRUSION_Z = -10
    EXTRUDED -> Clipper [CLIPPEE]
Clipper
    LINES_AS_SEGMENTS = No
    ATTR_ACCUM_MODE = Merge Clipper
    DEFAULT_VAL = 0
    BOUNDARY_CASES = Treat as Inside
    VAL_SOURCE = Clippee Only
    CLIP_TYPE = Multiple Clippers
    ATTR_CONFLICT_RES = Use Clippee
    CONNECT_Z_MODE = First Wins
    CLIPPED_ATTR = _clipped
    CREATE_AGGREGATES = Yes
    MEASURE_TYPE = Continuous
    MISSING_VAL_MODE = Compute
    PRESERVE_CLIPPEE_EXTENTS = No
    INSIDE -> Solid2surface [GeometryPartExtractor_3_Input]
    <REJECTED> -> Clipper__Rejected__2
Solid2surface
    GeometryRefiner_2_Output -> normalFinder [CoordinateCounter_2_Input]
normalFinder
    AttributeRemover_2_Output -> TestFilter_3
TestFilter_3
    TEST_LIST = BOOL_OP,OR,COMPOSITE_TEST,<Unused>,TEST_CLAUSE,"TEST @Value(_vz) > 0",UpLooking
    DEFAULT_VALUE = <UNFILTERED>
    UpLooking -> Counter_3
Counter_3
    DOMAIN = counter
    SCOPE = Local
    CNT_ATTR = _count_IDtoMerge
    START = 0
    -> AttributeKeeper
AttributeKeeper
    KEEP_ATTRS = _count_IDtoMerge
    -> SurfaceFootprintReplacer_2
    -> CoordinateExtractor_5
CoordinateExtractor_5
    MODE = All Coordinates
    IND = 0
    Y_ATTR = _y
    X_ATTR = _x
    LIST_NAME = _indices
    Z_ATTR = _z
    -> PythonCaller_TICcreator
Note: Need 2D
SurfaceFootprintReplacer_2
    LIGHT_Z = 1
    LIGHT_Y = 0
    LIGHT_X = 0
    SHADOW_MODE = Overhead Shadow
    OFFSET_Z = 0
    FOOTPRINT -> Dissolver
    FOOTPRINT -> GeometryCoercer
GeometryCoercer
    KIND = fme_line
    GQUERY:
      for $geom in //geometry
      where $geom/count(parent::geometry) = 0
      return number($geom/@fme_id)
    COERCED -> TopologyBuilder
Note: To split lines at nodes
TopologyBuilder
    CLEAN_DATA = No
    BOUNDING_EDGES = All
    OVERLAPPING_MODE = No
    DEAGGREGATE_INPUT = Yes
    MAX = 0
    PROP_ATTRS = No
    ALLOW_CYCLES = No
    LINE -> Clipper_2 [CLIPPEE]
Clipper_2
    LINES_AS_SEGMENTS = No
    ATTR_ACCUM_MODE = Merge Clipper
    DEFAULT_VAL = 0
    BOUNDARY_CASES = Treat as Inside
    VAL_SOURCE = Clippee Only
    CLIP_TYPE = Multiple Clippers
    ATTR_CONFLICT_RES = Use Clippee
    CONNECT_Z_MODE = First Wins
    CLIPPED_ATTR = _clipped
    CREATE_AGGREGATES = Yes
    MEASURE_TYPE = Continuous
    MISSING_VAL_MODE = Compute
    PRESERVE_CLIPPEE_EXTENTS = No
    OUTSIDE -> TestFilter_4
TestFilter_4
    TEST_LIST = BOOL_OP,OR,COMPOSITE_TEST,<Unused>,TEST_CLAUSE,"TEST @Value(_clipped) = no",outerBoundary
    DEFAULT_VALUE = <UNFILTERED>
    outerBoundary -> PythonCaller_edgeSorter
PythonCaller_edgeSorter
    PYTHONSYMBOL = FeatureProcessor
    PYTHONSOURCE:
      import fme
      import fmeobjects

      # Sorting edges counter-clockwise and creating points at each endpoint and vertex. From these points a TIC
      # can be created later.

      class FeatureProcessor(object):
          def __init__(self):
              # Using a dictionary to save the edges to make retrieval by edge id easier
              self.edgeDict = {}

          def input(self,feature):
              # Adding all line segments to the dictioanry
              self.edgeDict[feature.getAttribute('_edge_id')] = feature

          def close(self):
              orderedPoints = [] # List to place the points
              # Getting the lowest key to start with
              startEdgeKey = sorted(self.edgeDict)[0]
              # and retreiving the first edge (NB, pop removes the item)
              currentEdge = self.edgeDict.pop(startEdgeKey)
              # Adding the points of the line to the list
              orderedPoints.extend(currentEdge.getGeometry().getPoints())
              # and finding what edge is next
              nextEdge = currentEdge.getAttribute('_right_edge')

              # As long as there are edges in the dictionary
              while self.edgeDict:
                  currentEdge = self.edgeDict.pop(int(nextEdge))
                  # Since first point of current edge = last poitn of previous edge
                  # the first point is not added.
                  # NB, an edge can have a vertex i.e. more than two points
                  orderedPoints.extend(currentEdge.getGeometry().getPoints()[1:])
                  nextEdge = currentEdge.getAttribute('_right_edge')

              # Creating a line from the ordered list of points and returns
              pointXYZlist = [p.getXYZ() for p in orderedPoints]
              outLine = fmeobjects.FMELine(pointXYZlist)
              outFeature = fmeobjects.FMEFeature()
              outFeature.setGeometry(outLine)
              self.pyoutput(outFeature)




      '''

          def input(self,feature):
              if feature.getGeometry().getXYZ()[2] > self.maxZ:
                  self.maxZ = round(feature.getGeometry().getXYZ()[2])
              if feature.getAttribute('ground'):
                  self.groundPoints.append(feature)
              elif feature.getAttribute('roof'):
                  self.roofPoints.append(feature)
                  if feature.getAttribute('count') > self.nbrRoof:
                      self.nbrRoof = feature.getAttribute('count')

          def close(self):
              temp = self.roofPoints
              self.roofPoints = []
              # Splitting lower and upper roof in two lists
              for p in temp:
                  if round(p.getGeometry().getXYZ()[2]) == self.maxZ:
                      self.roofTop.append(p)
                  else:
                      self.roofPoints.append(p)

              tempPointList = [] # List with one nested list per roof part
              for roofPart in range(self.nbrRoof+1):
                  tempPointList.append([[],[]])


              # Adding point from the ground
              for p in self.groundPoints:
                  tempPointList[p.getAttribute('roofID')][0].append(p)

              # Adding point from the roof (lower part)
              for p in self.roofPoints:
                  tempPointList[p.getAttribute('count')][1].append(p)

              # Creating wall segments of the two sides
              for roofPart in range(self.nbrRoof+1):
                  tempXY = tempPointList[roofPart][0][-1].getGeometry().getXYZ()[0]
                  # Need to check that the order is correct in upper and lower part of the wall
                  if tempPointList[roofPart][1][0].getGeometry().getXYZ()[0] == tempXY: #Keeping order
                      tempPolyLineList = [tempPointList[roofPart][0][0].getGeometry().getXYZ(), tempPointList[roofPart][0][1].getGeometry().getXYZ(), tempPointList[roofPart][1][0].getGeometry().getXYZ(), tempPointList[roofPart][1][1].getGeometry().getXYZ()]
                      tempPolyLine = fmeobjects.FMELine(tempPolyLineList)
                  else: # Changing order
                      tempPolyLineList = [tempPointList[roofPart][0][0].getGeometry().getXYZ(), tempPointList[roofPart][0][1].getGeometry().getXYZ(), tempPointList[roofPart][1][1].getGeometry().getXYZ(), tempPointList[roofPart][1][0].getGeometry().getXYZ()]
                      tempPolyLine = fmeobjects.FMELine(tempPolyLineList)

                  tempWall = fmeobjects.FMEPolygon(tempPolyLine)

                  newFeatureWall = fmeobjects.FMEFeature()
                  newFeatureWall.setGeometry(tempWall)
                  newFeatureWall.setAttribute('roofID', roofPart)
                  newFeatureWall.setAttribute('wallID', self.wid)
                  self.wid += 1

                  self.pyoutput(newFeatureWall)

              # Creating wall segments of the two gable sides
              startside = 0 # Which wall side to start at
              endside = 1
              for gable in range(2):
                  # Starting with roof corner
                  tl = [] # List for the coordimates
                  tl.append(tempPointList[startside][1][-1])

                  tempXY = round(tl[0].getGeometry().getXYZ()[0]), round(tl[0].getGeometry().getXYZ()[1])
                  tempGable = tl[0].getAttribute('count')
                  # Want to find the next point which is a point with same (x,y) among the ground points.
                  for p in tempPointList[startside][0]:
                      if round(p.getGeometry().getXYZ()[0]) == tempXY[0] and round(p.getGeometry().getXYZ()[1]) == tempXY[1]:
                          tl.append(p)
                          break

                  # Next point should be the closest point that belong to the opposite roof segment.
                  # (straight shorter than diagonal)
                  tempDist = 99999999999999999999999999999999999
                  tempPoint = None
                  for p in tempPointList[endside][0]:
                      d = sqrt((tempXY[0]-p.getGeometry().getXYZ()[0])**2 + (tempXY[1]-p.getGeometry().getXYZ()[1])**2)
                      if d < tempDist and d > 10:
                          tempDist = d
                          tempPoint = p

                  tl.append(tempPoint)

                  # And the point straight above....
                  tempXY = round(tempPoint.getGeometry().getXYZ()[0]), round(tempPoint.getGeometry().getXYZ()[1])
                  # Want to find the next point which is a point with same (x,y) among the ground points.
                  for p in tempPointList[endside][1]:
                       if round(p.getGeometry().getXYZ()[0]) == tempXY[0] and round(p.getGeometry().getXYZ()[1]) == tempXY[1]:
                          tl.append(p)
                          break

                  # Finally finding the point on the rooftop
                  tempXY = round(tl[-1].getGeometry().getXYZ()[0]), round(tl[-1].getGeometry().getXYZ()[1])
                  tempDist = 99999999999999999999999999999999999
                  tempPoint = None
                  for rt in self.roofTop:
                      d = sqrt((tempXY[0]-rt.getGeometry().getXYZ()[0])**2 + (tempXY[1]-rt.getGeometry().getXYZ()[1])**2)
                      if d < tempDist:
                          tempDist = d
                          tempPoint = rt

                  tl.append(tempPoint)

                  tpl = [tl[0].getGeometry().getXYZ(), tl[1].getGeometry().getXYZ(), tl[2].getGeometry().getXYZ(), tl[3].getGeometry().getXYZ(), tl[4].getGeometry().getXYZ()]
                  tp = fmeobjects.FMELine(tpl)
                  tw = fmeobjects.FMEPolygon(tp)

                  nfw = fmeobjects.FMEFeature()
                  nfw.setGeometry(tw)
                  nfw.setAttribute('wallID', self.wid)
                  self.wid += 1

                  # Swapping to start on "the other" side
                  startside = 1 # Which wall side to start at
                  endside = 0

                  self.pyoutput(nfw)


      '''






      '''
              for f in self.featureList:
                  # Getting the attribute with json
                  jsonData = f.getAttribute('_response_body_caller4')

                  jsonOut = json.loads(jsonData)

                  print jsonOut

                  f.setAttribute("href", jsonOut['href'])

                  jsonData = jsonOut['data']
                  for key in jsonData:
                      f.setAttribute(key, jsonData[key])

                  self.pyoutput(f)
      '''
    -> AttributeCreator
AttributeCreator
    ATTR_TABLE = SET_TO OrderedPoints = 1
    -> AttributeKeeper_2
AttributeKeeper_2
    KEEP_ATTRS = OrderedPoints
    -> PythonCaller_TICcreator
Note: Creating Terrain intersection line
PythonCaller_TICcreator
    PYTHONSYMBOL = FeatureProcessor
    PYTHONSOURCE:
      import fme
      import fmeobjects
      from math import sqrt

      # Sorting edges counter-clockwise and creating points at each endpoint and vertex. From these points a TIC
      # can be created later.

      def zValueFinder(tempPoint, co, eps):
          # Searching until we find. Set tolerance to 1 cm
          for idx in xrange(len(co)):
              tempDist = sqrt((tempPoint[0]-co[idx][0])**2 + (tempPoint[1]-co[idx][1])**2)
              if tempDist < eps:
                  return co[idx][2]


      class FeatureProcessor(object):
          def __init__(self):
              self.coordinateList = []
              self.orderedPoints = None

          def input(self,feature):
              if feature.getAttribute('OrderedPoints'):
                  self.orderedPoints = feature
              else:
                  # Long way to get points of the verties........
                  # NB, removes first point sice polygon is closed
                  geo = feature.getGeometry().getAsArea().getBoundaryAsCurve().getPoints()[1:]
                  geoXYZ = [p.getXYZ() for p in geo]
                  self.coordinateList.extend(geoXYZ)



          def close(self):
              # Creating the terrain intersection line (TIC)
              ticList = []
              ticGeo = self.orderedPoints.getGeometry().getPoints()
              ticGeo = [p.getXYZ() for p in ticGeo]

              # Iterating over all points of the line to find the z-value
              for tempXYZ in ticGeo:
                  # Finds the z-value for the current point. 0.01 is the tolerance
                  # i.e. if a point is withoin 1 dm in xy-distance from the current
                  # it is considered to be the same and z is returned.
                  tempZ = zValueFinder(tempXYZ, self.coordinateList, 0.1)
                  ticList.append((tempXYZ[0], tempXYZ[1], tempZ))


              # Creating the TIC from the list of (x,y,z) tuples
              outLine = fmeobjects.FMELine(ticList)
              outFeature = fmeobjects.FMEFeature()
              outFeature.setGeometry(outLine)
              self.pyoutput(outFeature)




      '''

          def input(self,feature):
              if feature.getGeometry().getXYZ()[2] > self.maxZ:
                  self.maxZ = round(feature.getGeometry().getXYZ()[2])
              if feature.getAttribute('ground'):
                  self.groundPoints.append(feature)
              elif feature.getAttribute('roof'):
                  self.roofPoints.append(feature)
                  if feature.getAttribute('count') > self.nbrRoof:
                      self.nbrRoof = feature.getAttribute('count')

          def close(self):
              temp = self.roofPoints
              self.roofPoints = []
              # Splitting lower and upper roof in two lists
              for p in temp:
                  if round(p.getGeometry().getXYZ()[2]) == self.maxZ:
                      self.roofTop.append(p)
                  else:
                      self.roofPoints.append(p)

              tempPointList = [] # List with one nested list per roof part
              for roofPart in range(self.nbrRoof+1):
                  tempPointList.append([[],[]])


              # Adding point from the ground
              for p in self.groundPoints:
                  tempPointList[p.getAttribute('roofID')][0].append(p)

              # Adding point from the roof (lower part)
              for p in self.roofPoints:
                  tempPointList[p.getAttribute('count')][1].append(p)

              # Creating wall segments of the two sides
              for roofPart in range(self.nbrRoof+1):
                  tempXY = tempPointList[roofPart][0][-1].getGeometry().getXYZ()[0]
                  # Need to check that the order is correct in upper and lower part of the wall
                  if tempPointList[roofPart][1][0].getGeometry().getXYZ()[0] == tempXY: #Keeping order
                      tempPolyLineList = [tempPointList[roofPart][0][0].getGeometry().getXYZ(), tempPointList[roofPart][0][1].getGeometry().getXYZ(), tempPointList[roofPart][1][0].getGeometry().getXYZ(), tempPointList[roofPart][1][1].getGeometry().getXYZ()]
                      tempPolyLine = fmeobjects.FMELine(tempPolyLineList)
                  else: # Changing order
                      tempPolyLineList = [tempPointList[roofPart][0][0].getGeometry().getXYZ(), tempPointList[roofPart][0][1].getGeometry().getXYZ(), tempPointList[roofPart][1][1].getGeometry().getXYZ(), tempPointList[roofPart][1][0].getGeometry().getXYZ()]
                      tempPolyLine = fmeobjects.FMELine(tempPolyLineList)

                  tempWall = fmeobjects.FMEPolygon(tempPolyLine)

                  newFeatureWall = fmeobjects.FMEFeature()
                  newFeatureWall.setGeometry(tempWall)
                  newFeatureWall.setAttribute('roofID', roofPart)
                  newFeatureWall.setAttribute('wallID', self.wid)
                  self.wid += 1

                  self.pyoutput(newFeatureWall)

              # Creating wall segments of the two gable sides
              startside = 0 # Which wall side to start at
              endside = 1
              for gable in range(2):
                  # Starting with roof corner
                  tl = [] # List for the coordimates
                  tl.append(tempPointList[startside][1][-1])

                  tempXY = round(tl[0].getGeometry().getXYZ()[0]), round(tl[0].getGeometry().getXYZ()[1])
                  tempGable = tl[0].getAttribute('count')
                  # Want to find the next point which is a point with same (x,y) among the ground points.
                  for p in tempPointList[startside][0]:
                      if round(p.getGeometry().getXYZ()[0]) == tempXY[0] and round(p.getGeometry().getXYZ()[1]) == tempXY[1]:
                          tl.append(p)
                          break

                  # Next point should be the closest point that belong to the opposite roof segment.
                  # (straight shorter than diagonal)
                  tempDist = 99999999999999999999999999999999999
                  tempPoint = None
                  for p in tempPointList[endside][0]:
                      d = sqrt((tempXY[0]-p.getGeometry().getXYZ()[0])**2 + (tempXY[1]-p.getGeometry().getXYZ()[1])**2)
                      if d < tempDist and d > 10:
                          tempDist = d
                          tempPoint = p

                  tl.append(tempPoint)

                  # And the point straight above....
                  tempXY = round(tempPoint.getGeometry().getXYZ()[0]), round(tempPoint.getGeometry().getXYZ()[1])
                  # Want to find the next point which is a point with same (x,y) among the ground points.
                  for p in tempPointList[endside][1]:
                       if round(p.getGeometry().getXYZ()[0]) == tempXY[0] and round(p.getGeometry().getXYZ()[1]) == tempXY[1]:
                          tl.append(p)
                          break

                  # Finally finding the point on the rooftop
                  tempXY = round(tl[-1].getGeometry().getXYZ()[0]), round(tl[-1].getGeometry().getXYZ()[1])
                  tempDist = 99999999999999999999999999999999999
                  tempPoint = None
                  for rt in self.roofTop:
                      d = sqrt((tempXY[0]-rt.getGeometry().getXYZ()[0])**2 + (tempXY[1]-rt.getGeometry().getXYZ()[1])**2)
                      if d < tempDist:
                          tempDist = d
                          tempPoint = rt

                  tl.append(tempPoint)

                  tpl = [tl[0].getGeometry().getXYZ(), tl[1].getGeometry().getXYZ(), tl[2].getGeometry().getXYZ(), tl[3].getGeometry().getXYZ(), tl[4].getGeometry().getXYZ()]
                  tp = fmeobjects.FMELine(tpl)
                  tw = fmeobjects.FMEPolygon(tp)

                  nfw = fmeobjects.FMEFeature()
                  nfw.setGeometry(tw)
                  nfw.setAttribute('wallID', self.wid)
                  self.wid += 1

                  # Swapping to start on "the other" side
                  startside = 1 # Which wall side to start at
                  endside = 0

                  self.pyoutput(nfw)


      '''






      '''
              for f in self.featureList:
                  # Getting the attribute with json
                  jsonData = f.getAttribute('_response_body_caller4')

                  jsonOut = json.loads(jsonData)

                  print jsonOut

                  f.setAttribute("href", jsonOut['href'])

                  jsonData = jsonOut['data']
                  for key in jsonData:
                      f.setAttribute(key, jsonData[key])

                  self.pyoutput(f)
      '''
    -> PythonCaller_TICcreator_Output
    -> GeometryExtractor_terrainIntersectionLine
PythonCaller_TICcreator_Output: Inspector
Note: Add this to GML writer to add the terrain intersection line to the model.
Note: To get GML 3.1.1 geometry
GeometryExtractor_terrainIntersectionLine
    OGC_WKT_PRECISION_DISPLAY = Shortened 64-bit
    OGCVERSION = 1.2
    KIND_LONG = GML v3.1.1
    OMIT_NAMESPACES_DISPLAY = No
    ATTR = _geometry
    OGEOSMS_URL_PREFIX = http://maps.google.com/?q=
    PREFER_POLYGON_OVER_SURFACE = No
    REMOVE_GEOMETRY = No
    -> U_huset_LOD23 (writer GML_1)
Clipper__Rejected__2: Inspector

Bookmark: To clip the interior
Dissolver
    ACCUM_INPUT_ATTRS = Use Attributes From One Feature
    DEAGGREGATE_INPUT = Yes
    CONNECT_Z_MODE = First Wins
    NO_OVRLP = No
    AREA -> Bufferer_2
Bufferer_2
    CAP_STYLE = Round
    CORNER_STYLE = Round
    OFFSET = -1
    ANGLE = 22.5
    BUFFERED -> Clipper_2 [CLIPPER]

FME custom transformer normalFinder

CoordinateCounter_2_Input (input)
    -> CoordinateCounter_2
AttributeRemover_2_Output (output)

Bookmark: Calculate Normal Vector (_vx, _vy, _vz)
  There was a special case with one outer wall surface (see notes) which gave wrong orientation due to concave shape. This version is using coordinates with index 0, 1, (nbr coords -4) to test if that solves the problem. See notes for more details.
Note: Need to know the number of / coordinates to find the second / last.
CoordinateCounter_2
    CNT_ATTR = _coordcount_normal_vector
    -> CoordinateExtractor_2
CoordinateExtractor_2
    IND = 0
    Z_DEFAULT = -9999
    Y_ATTR = _y0
    X_ATTR = _x0
    Z_ATTR = _z0
    -> CoordinateExtractor_3
CoordinateExtractor_3
    IND = 1
    Z_DEFAULT = -9999
    Y_ATTR = _y1
    X_ATTR = _x1
    Z_ATTR = _z1
    -> CoordinateExtractor_4
CoordinateExtractor_4
    IND = @Value(_coordcount_normal_vector)-2
    Z_DEFAULT = -9999
    Y_ATTR = _y2
    X_ATTR = _x2
    Z_ATTR = _z2
    -> AttributeCreator_2
AttributeCreator_2
    ATTR_LIST = _vx0,@Evaluate(@Value(_x1)-@Value(_x0)),_vy0,@Evaluate(@Value(_y1)-@Value(_y0)),_vz0,@Evaluate(@Value(_z1)-@Value(_z0)),_vx1,@Evaluate(@Value(_x2)-@Value(_x0)),_vy1,@Evaluate(@Value(_y2)-@Value(_y0)),_vz1,@Evaluate(@Value(_z2)-@Value(_z0))
    -> AttributeCreator_3
AttributeCreator_3
    ATTR_LIST = _vx,@Evaluate(@Value(_vy0)*@Value(_vz1)-@Value(_vz0)*@Value(_vy1)),_vy,@Evaluate(@Value(_vz0)*@Value(_vx1)-@Value(_vx0)*@Value(_vz1)),_vz,@Evaluate(@Value(_vx0)*@Value(_vy1)-@Value(_vy0)*@Value(_vx1))
    -> AttributeRemover_2
AttributeRemover_2
    REMOVE_ATTRS = _coordcount_normal_vector
    -> AttributeRemover_2_Output (output)

FME custom transformer Solid2surface

GeometryPartExtractor_3_Input (input)
    -> GeometryPartExtractor_3

Bookmark: To get surfaces from the solids
Note: Check that geometry name is solid
GeometryPartExtractor_3
    EXTRACTTYPE_PARAM = Extract
    GQUERY:
      for $geom in //geometry
      where $geom/@fme_geometry_name = 'Body'
      return number($geom/@fme_id)
    PROCESSED -> GeometryCoercer_3
    UNTOUCHED -> GeometryCoercer_3
Note: Check for geometry type IFMEExtrusion OR IFMEBRepSolid
GeometryCoercer_3
    KIND = fme_composite_surface
    GQUERY:
      for $geom in //geometry
      where $geom/@fme_geometry_type = 'IFMEExtrusion'
      or $geom/@fme_geometry_type = 'IFMEBRepSolid'
      return number($geom/@fme_id)
    COERCED -> Deaggregator_3
    UNTOUCHED -> Deaggregator_3
Note: Changed split compostites to YES
Deaggregator_3
    MODE = Flatten All Levels
    SPLIT_COMPOSITES = Yes
    GEOM_NAME_FIELD = _geometry_name
    EXPLODE_INSTANCES = No
    LIST_ATTR_MODE_LOOKUP = LEAN
    DEAGGREGATED -> GeometryRefiner_2
Note: Keep this or not?
GeometryRefiner_2
    -> GeometryRefiner_2_Output (output)
GeometryRefiner_2_Output (output)

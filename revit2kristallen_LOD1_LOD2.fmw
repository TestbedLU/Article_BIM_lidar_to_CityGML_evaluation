FME workspace revit2kristallen_LOD1_LOD2.fmw
Title: revit2kristallen_LOD1_LOD2

Parameters:
- SourceDataset_REVIT = D:\Temp\A40 Kristallen 1 Lund_Relationshandling.ifc   # Source Revit Export File(s)
- GroundLevel = 42.48   # Ground level of the building
- DestDataset_GML = D:\Testbed\Jings_project\Kristallen\Kristallen_lod_1_2.gml   # Destination Geography Markup Language (GML) File

Readers:
- REVIT_1: REVIT from $(SourceDataset_REVIT)

Writers:
- GML_1: GML to $(DestDataset_GML)
- GML_2: GML to $(DestDataset_GML)

Roof (reader REVIT_1)
    attributes: element_parent_id char(200), element_id char(200), GlobalId char(200), Name char(200), ObjectType char(200), Tag char(200), Analytical Properties.Absorptance double, Analytical Properties.Roughness double, Constraints.Base Level char(200), Constraints.Base Offset From Level double, Constraints.Cutoff Offset double, Constraints.Related to Mass logical, Constraints.Room Bounding logical, Construction.Default Thickness double, Construction.Fascia Depth double, Construction.Maximum Ridge Height double, Construction.Rafter Cut char(200), Dimensions.Area double, Dimensions.Thickness double, Dimensions.Volume double, Graphics.Coarse Scale Fill Color integer, Identity Data.Assembly Code char(200), Identity Data.Assembly Description char(200), Phasing.Phase Created char(200), Pset_RoofCommon.IsExternal logical, Pset_RoofCommon.ProjectedArea double, Pset_RoofCommon.Reference char(200), Pset_RoofCommon.TotalArea double, Pset_ManufacturerTypeInformation.Manufacturer char(200), Pset_ManufacturerTypeInformation.ModelLabel char(200),
      Pset_ManufacturerTypeInformation.ModelReference char(200), Pset_ManufacturerTypeInformation.ProductionYear char(200)
    -> TestFilter_3
Junction
    -> Junction_2
Note: AttributeRenamer : Output
Junction_2
    -> Aggregator_lower_roof
Note: Lund City Hall (Kristallen) to LOD1 and LOD2 / This workspace is released under the 3-Clause BSD License. For details, see the Description of this workspace. See also https://opensource.org/licenses/BSD-3-Clause / This script reads an IFC model and tranforms it to LOD1 and LOD2 CityGML building model geometry (GML 3.1.1). The IFC model is not included with the workbench. / Roof and slab elements are used to extract the footprint of the building. / The ground level of the building is given as a user parameter since it cannot be derived from the IFC model. / For suggested detailed LOD definitions (LOD2.3) see: / Biljecki, F., Ledoux, H., Stoter, J., 2016a. An improved LOD specification for 3D building models. Computers, Environment, and Urban Systems, vol. 59, pp. 25-37. https://doi.org/10.3390/ijgi4042842. / The workbench is created with FME version 2017.1.2.1
Slab (reader REVIT_1)
    attributes: element_parent_id char(200), element_id char(200), GlobalId char(200), Name char(200), ObjectType char(200), Tag char(200), OverallHeight double, OverallWidth double, Analytical Properties.Absorptance double, Analytical Properties.Roughness double, BaseQuantities.GrossArea double, BaseQuantities.GrossVolume double, BaseQuantities.Perimeter double, BaseQuantities.Width double, Constraints.Base Level char(200), Constraints.Base Offset From Level double, Constraints.Cutoff Offset double, Constraints.Height Offset From Level double, Constraints.Level char(200), Constraints.Related to Mass logical, Constraints.Room Bounding logical, Construction.Default Thickness double, Construction.Fascia Depth double, Construction.Function char(200), Construction.Maximum Ridge Height double, Construction.Rafter Cut char(200), Construction.Rafter or Truss char(200), Construction.Thickness double, Dimensions.Area double, Dimensions.Perimeter double,
      Dimensions.Slope double, Dimensions.Thickness double, Dimensions.Volume double, Graphics.Coarse Scale Fill Color double, Identity Data.Assembly Code char(200), Identity Data.Assembly Description char(200), Materials and Finishes.Structural Material char(200), Phasing.Phase Created char(200), Pset_RoofCommon.IsExternal logical, Pset_RoofCommon.ProjectedArea double, Pset_RoofCommon.Reference char(200), Pset_RoofCommon.TotalArea double, Pset_SlabCommon.IsExternal logical, Pset_SlabCommon.LoadBearing logical, Pset_SlabCommon.Reference char(200), Pset_ManufacturerTypeInformation.Manufacturer char(200), Pset_ManufacturerTypeInformation.ModelLabel char(200), Pset_ManufacturerTypeInformation.ModelReference char(200), Pset_ManufacturerTypeInformation.ProductionYear char(200)
    -> TestFilter
Note: Filtering out elements that / are not part of the building / such as roads and vegetation
TestFilter
    TEST_LIST:
      BOOL_OP,OR,COMPOSITE_TEST,<Unused>,TEST_CLAUSE,"TEST @Value(ObjectType) CONTAINS gbana",Roads,BOOL_OP,OR,COMPOSITE_TEST,<Unused>,TEST_CLAUSE,"TEST @Value(ObjectType) CONTAINS egitation",Vegetation,BOOL_OP,OR,COMPOSITE_TEST,<Unused>,TEST_CLAUSE,"TEST @Value(Name) CONTAINS etong",Betong,BOOL_OP,OR,COMPOSITE_TEST,<Unused>,TEST_CLAUSE,"TEST @Value(Name) CONTAINS oncrete",Concrete,BOOL_OP,OR,COMPOSITE_TEST,<Unused>,TEST_CLAUSE,"TEST @Value(Name) CONTAINS olyuretan",Polyuretan,BOOL_OP,OR,COMPOSITE_TEST,<Unused>,TEST_CLAUSE,"TEST @Value(Name) = Basic Roof:Roof Construction - 400mm:4415741
      TEST @Value(Name) = Floor:Plattbärlag 200+50mm:4335787
      TEST @Value(Name) = Floor:Klinker 96x96:6359377
      TEST @Value(Name) = Basic Roof:Tak Hiss:6489549",Others
    DEFAULT_VALUE = <UNFILTERED>
    <UNFILTERED> -> TestFilter_7
    <UNFILTERED> -> TestFilter_mainRoofSlab
Note: Hard coded to get the main roof slab i.e. the / main roof excl. the lower part. / Could be directly connected to slab reader....
TestFilter_mainRoofSlab
    TEST_LIST = BOOL_OP,OR,COMPOSITE_TEST,<Unused>,TEST_CLAUSE,"TEST @Value(element_id) = 3o9C$vrQH7nwLnxmiyNTiF",mainPart
    DEFAULT_VALUE = <UNFILTERED>
    mainPart -> SurfaceFootprintReplacer_mainRoofSlab
SurfaceFootprintReplacer_mainRoofSlab
    OFFSET_Z = 0
    SHADOW_MODE = Overhead Shadow
    FOOTPRINT -> DonutHoleExtractor
DonutHoleExtractor
    DEAGGREGATE_INPUT = Yes
    OUTERSHELL -> Clipper [CLIPPER]
    <REJECTED> -> DonutHoleExtractor__Rejected_
DonutHoleExtractor__Rejected_: Inspector
Note: Extracting slabs of interest
TestFilter_7
    TEST_LIST:
      BOOL_OP,OR,COMPOSITE_TEST,<Unused>,TEST_CLAUSE,"TEST @Value(element_id) = 0QTYhbuOTBvR8O_pFL11V6
      TEST @Value(element_id) = 3o9C$vrQH7nwLnxmiyNTiF",slabAll
    DEFAULT_VALUE = <UNFILTERED>
    slabAll -> Aggregator_2
Note: Merging with roof to get height
Aggregator_2
    MODE = Geometry - Assemble One Level
    AGGREGATE_TYPE = Homogeneous Collection (If Possible)
    ACCUM_ATTRS_NAME = Merge Incoming Attributes
    ORDERED = No
    SEP = ,
    AGGREGATE -> SurfaceFootprintReplacer_building
SurfaceFootprintReplacer_building
    OFFSET_Z = 0
    SHADOW_MODE = Overhead Shadow
    FOOTPRINT -> Clipper [CLIPPEE]
    FOOTPRINT -> Junction_5
Note: To split into main roof and the lower / part of the roof. Clippee is entire building / footprint, Clipper is main part of the footprint / i.e. excl. the lower roof.
Clipper
    CONNECT_Z_MODE = First Wins
    ATTR_ACCUM_MODE = Merge Clipper
    CLIP_TYPE = Multiple Clippers
    MISSING_VAL_MODE = Compute
    CREATE_AGGREGATES = Yes
    DEFAULT_VAL = 0
    ATTR_CONFLICT_RES = Use Clippee
    LINES_AS_SEGMENTS = No
    VAL_SOURCE = Clippee Only
    BOUNDARY_CASES = Treat as Inside
    CLIPPED_ATTR = _clipped
    PRESERVE_CLIPPEE_EXTENTS = No
    MEASURE_TYPE = Continuous
    INSIDE -> Scaler_2
    OUTSIDE -> Aggregator_lower_roof
Note: Merging with roof to get height
Aggregator_lower_roof
    MODE = Geometry - Assemble One Level
    AGGREGATE_TYPE = Homogeneous Collection (If Possible)
    ACCUM_ATTRS_NAME = Merge Incoming Attributes
    ORDERED = No
    SEP = ,
    AGGREGATE -> SurfaceFootprintReplacer
SurfaceFootprintReplacer
    OFFSET_Z = 0
    SHADOW_MODE = Overhead Shadow
    LIGHT_X = 0
    LIGHT_Y = 0
    LIGHT_Z = 1
    FOOTPRINT -> Scaler_3
SolidDissolver
    Sum_1:
      from re import sub
      if (FME_MacroValues['Sum']==''):
          return "pyfme_none"
      else:
          Sum=sub(","," ",FME_MacroValues['Sum'],)
          return Sum
    ACCUM_ATTRS_NAME = No
    Av_1:
      from re import sub
      if (FME_MacroValues['Av']==''):
          return "pyfme_none"
      else:
          Av=sub(","," ",FME_MacroValues['Av'],)
          return Av
    Group_1:
      from re import sub
      if (FME_MacroValues['Group']==''):
          return "pyfme_none"
      else:
          group=sub(","," ",FME_MacroValues['Group'],)
          return group
    Concat_1:
      from re import sub
      if (FME_MacroValues['Concat']==''):
          return "pyfme_none"
      else:
          Concat=sub(","," ",FME_MacroValues['Concat'],)
          return Concat
    SEP = ,
    List_1:
      if FME_MacroValues['List'] == "":
          return "pyfme_list"
      else:
          return FME_MacroValues['List']
    Dissolved -> GeometryExtractor_LOD13
Note: To get GML 3.1.1 geometry
GeometryExtractor_LOD13
    OGC_WKT_PRECISION_DISPLAY = Shortened 64-bit
    OGCVERSION = 1.2
    OMIT_NAMESPACES_DISPLAY = No
    ATTR = _geometry
    PREFER_POLYGON_OVER_SURFACE = No
    KIND_LONG = GML v3.1.1
    REMOVE_GEOMETRY = No
    OGEOSMS_URL_PREFIX = http://maps.google.com/?q=
    -> GML_LOD_1_3 (writer GML_2)
    -> GeometryExtractor_LOD13_Output
GeometryExtractor_LOD13_Output: Inspector
GML_LOD_1_3 (writer GML_2)
Note: For creating LOD1.2 model
Junction_5
    -> Junction_6

Bookmark: Getting heights for the three building parts (LOD1.3 and higher)
  Filtering out the three main parts of the roof and extracting height for these. Used later to extrude the three spearate building parts for LOD1.3 and higher.
TestFilter_3
    TEST_LIST = BOOL_OP,OR,COMPOSITE_TEST,<Unused>,TEST_CLAUSE,"TEST @Value(element_parent_id) = 0Kgv$YhZX3GxCiNz2PpDFU",mainRoof,BOOL_OP,OR,COMPOSITE_TEST,<Unused>,TEST_CLAUSE,"TEST @Value(element_parent_id) = 0Kgv$YhZX3GxCiNz2PoH6b",lowerRoof,BOOL_OP,OR,COMPOSITE_TEST,<Unused>,TEST_CLAUSE,"TEST @Value(element_parent_id) = 0Kgv$YhZX3GxCiNz2PpChl",highestTop
    DEFAULT_VALUE = <UNFILTERED>
    mainRoof -> Aggregator
    lowerRoof -> roofHeightExtractor_low [CoordinateExtractor_Input_1]
    highestTop -> roofHeightExtractor_high [CoordinateExtractor_Input_1]
Aggregator
    MODE = Geometry - Assemble One Level
    AGGREGATE_TYPE = Homogeneous Collection (If Possible)
    ACCUM_ATTRS_NAME = Use Attributes From One Feature
    ORDERED = No
    SEP = ,
    AGGREGATE -> roofHeightExtractor_main [CoordinateExtractor_Input_1]
roofHeightExtractor_main
    TestFilter_6_LargestRoof -> Aggregator_2
roofHeightExtractor_low
    TestFilter_6_LargestRoof -> AttributeRenamer
Note: Aggregator_lower_roof : Input
AttributeRenamer
    ATTR_TABLE:
      RENAME_SET_DEFAULT _max_z_roof > _max_z_roof_lower
      RENAME_SET_DEFAULT _min_z_roof > _min_z_roof_lower
    -> Junction
roofHeightExtractor_high
    TestFilter_6_LargestRoof -> AttributeRenamer_2
AttributeRenamer_2
    ATTR_TABLE:
      RENAME_SET_DEFAULT _max_z_roof > _max_z_roof_top
      RENAME_SET_DEFAULT _min_z_roof > _min_z_roof_top
    -> HullReplacer
HullReplacer
    HULLTYPE_PARAM = Convex ()
    3DMODE_PARAM = Automatic
    HULL -> SurfaceFootprintReplacer_2
SurfaceFootprintReplacer_2
    OFFSET_Z = 0
    SHADOW_MODE = Overhead Shadow
    LIGHT_X = 0
    LIGHT_Y = 0
    LIGHT_Z = 1
    FOOTPRINT -> AreaCalculator_2
AreaCalculator_2
    AREA_ATTR = _area_top
    MULT = 1
    AREA_TYPE = Plane Area
    -> Tester
Tester
    BOOL_OP = OR
    TEST_CLAUSE = TEST @Value(_area_top) > 10000000
    TEST_MODE = Automatic
    PASSED -> Junction_3
Note: Scaler_4 : Input
Junction_3
    -> Junction_4

Bookmark: Chaning scale and creating Solid LOD 1.3 (and LOD2.3)
  NB, here ground level is given as user parameter. Not given in the model.
  LOD2.3 is identical to LOD1.3 for Kristallen.
Note: SurfaceFootprintReplacer_2 : Footprint
Note: Not all the way down since it / needs to reach "inside" main part only
Junction_4
    -> Scaler_4

Bookmark: Top part
Scaler_4
    XSCALE = 0.001
    YSCALE = 0.001
    RASTER_SCALING = Extents
    TEXT_LOC_ONLY = Location and Size
    ZSCALE = 0.001
    SCALE_ORIGIN = 0,0
    SCALED -> Offsetter_4
Offsetter_4
    YOFF = 0
    XOFF = 0
    ZOFF = @Value(_max_z_roof_top)*0.001
    MODE = Cartesian Coordinate
    OFFSET -> AttributeCreator_3
AttributeCreator_3
    ATTR_TABLE = SET_TO extrusionDist = @Evaluate($(GroundLevel)-@Value(_max_z_roof_top)*0.001+2)
    -> Extruder_4
Extruder_4
    EXTRUSION_Y = 0.0
    EXTRUSION_Z = @Value(extrusionDist)
    EXTRUSION_X = 0.0
    DIRECTION = Specified
    EXTRUDED -> SolidDissolver [Solids]

Bookmark: Lower part
Scaler_3
    XSCALE = 0.001
    YSCALE = 0.001
    RASTER_SCALING = Extents
    TEXT_LOC_ONLY = Location and Size
    ZSCALE = 0.001
    SCALE_ORIGIN = 0,0
    SCALED -> Offsetter_3
Offsetter_3
    YOFF = 0
    XOFF = 0
    ZOFF = @Value(_max_z_roof_lower)*0.001
    MODE = Cartesian Coordinate
    OFFSET -> AttributeCreator_2
AttributeCreator_2
    ATTR_TABLE = SET_TO extrusionDist = @Evaluate($(GroundLevel)-@Value(_max_z_roof_lower)*0.001)
    -> Extruder_3
Extruder_3
    EXTRUSION_Y = 0.0
    EXTRUSION_Z = @Value(extrusionDist)
    EXTRUSION_X = 0.0
    DIRECTION = Specified
    EXTRUDED -> SolidDissolver [Solids]

Bookmark: Main part
Scaler_2
    XSCALE = 0.001
    YSCALE = 0.001
    RASTER_SCALING = Extents
    TEXT_LOC_ONLY = Location and Size
    ZSCALE = 0.001
    SCALE_ORIGIN = 0,0
    SCALED -> Offsetter_2
Offsetter_2
    YOFF = 0
    XOFF = 0
    ZOFF = @Value(_max_z_roof)*0.001
    MODE = Cartesian Coordinate
    OFFSET -> AttributeCreator
AttributeCreator
    ATTR_TABLE = SET_TO extrusionDist = @Evaluate($(GroundLevel)-@Value(_max_z_roof)*0.001)
    -> Extruder_2
Extruder_2
    EXTRUSION_Y = 0.0
    EXTRUSION_Z = @Value(extrusionDist)
    EXTRUSION_X = 0.0
    DIRECTION = Specified
    EXTRUDED -> SolidDissolver [Solids]

Bookmark: Creating LOD1.2 model from footprint of building
Note: SurfaceFootprintReplacer_4 : Footprint
Junction_6
    -> Generalizer
Note: Generalizing the footprint. / Now there are two small dents removed.
Generalizer
    ALG_TEXT = Douglas (Generalize)
    TOLERANCE = 1000
    PRESERVE = No
    -> Scaler
Note: To get GML 3.1.1 geometry
GeometryExtractor_LOD12
    OGC_WKT_PRECISION_DISPLAY = Shortened 64-bit
    OGCVERSION = 1.2
    OMIT_NAMESPACES_DISPLAY = No
    ATTR = _geometry
    PREFER_POLYGON_OVER_SURFACE = No
    KIND_LONG = GML v3.1.1
    REMOVE_GEOMETRY = No
    OGEOSMS_URL_PREFIX = http://maps.google.com/?q=
    -> GML_LOD_1_2 (writer GML_1)
    -> GeometryExtractor_LOD12_Output
GeometryExtractor_LOD12_Output: Inspector
GML_LOD_1_2 (writer GML_1)

Bookmark: Chaning scale and creating Solid LOD 1.2
  NB, here ground level is given as user parameter. Not given in the model.
Scaler
    XSCALE = 0.001
    YSCALE = 0.001
    RASTER_SCALING = Extents
    TEXT_LOC_ONLY = Location and Size
    ZSCALE = 0.001
    SCALE_ORIGIN = 0,0
    SCALED -> Offsetter
Offsetter
    YOFF = 0
    XOFF = 0
    ZOFF = @Value(_max_z_roof)*0.001
    MODE = Cartesian Coordinate
    OFFSET -> Extruder
Extruder
    EXTRUSION_Y = 0.0
    EXTRUSION_Z = (@Value(_max_z_roof)*0.001 - $(GroundLevel))*-1
    EXTRUSION_X = 0.0
    DIRECTION = Specified
    EXTRUDED -> GeometryExtractor_LOD12

FME custom transformer SolidDissolver
The SolidDissolver dissolves adjoining solids into a single feature. Any non-solid geometries will be output untouched through the <Rejected> port.
The SolidDissolver has the following parameters:
    Group By
If you do not select Group By attributes, then all features fall into the same group.
When you select Group By attributes, this transformer will dissolve the geometries of the input solid features, based on the selection in the Group By parameter. Each group of features that have the same values for the Group By attributes will be processed independently of other groups.
    Count Attribute
If a Count Attribute is entered, then an attribute with this name will be added to each output solid, containing the number of features that resulted in the output solid.
    Keep Input Attributes
If Keep Input Attributes is set to Yes, the attributes from the original features will be merged onto the output Dissolved features.
    List Name
If a List Name is specified, then all attributes of an input feature will be stored as part of a list attribute entry in the output Dissolved feature.
    Attributes to Concatenate
Attributes can be concatenated so that the resulting Dissolved feature preserves multiple source attribute values under the same attribute name. For example, if input feature 1 has an id attribute of 1 and input feature 2 has an id attribute of 2, specifying id for this parameter together with a separate character of , will cause the output Dissolved feature to have an id with value 1, 2.
    Separator Character
The Separator Character is used to separate elements within an attribute value string. For example, if features with attribute values of 'River Rd', 'Marine Dr' and 'HWY 1' for the attribute named 'Road Name' respectively, and the Separator Character is , (a comma followed by a space) on the output solid feature, the attribute 'Road Name' will contain 'River Rd, Marine Dr, HWY 1' as a value.
The separator character can be expressed as a regular character but it can also contain special characters beginning with a backslash ("\"), as specified in the following table.
If the sequence is not listed in the table, the backslash character is ignored. (For example, entering lan\es will be interpreted as lanes.) If no separator character is supplied, attributes will be concatenated without a separator.
    Sequence
    Description
\a Audible alert (bell) (0x07)
\b Backspace (0x08)
\f Form feed (0x0c)
\n Newline (0x0a)
\r Carriage return (0x0d)
\t Tab (0x09)
\v Vertical tab (0x0b)
\\ Backslash
(Note: A single backslash entered at the end of a value will be converted to an escaped backslash.)
    Attributes to Sum
Any attributes specified in this field will undergo statistical accumulation.
For example, if two input solids have an attribute 'salary' set to 30000 and 50000, then summing them would result in a 'salary' of 80000 on the dissolved output.
    Attributes to Average
Any attributes specified in this field will undergo statistical accumulation.
For example, if two input solids have an attribute 'salary' set to 30000 and 50000, then averaging them would result in a 'salary' of 40000 on the dissolved output.

Parameters:
- Group =   # " " Group By
- COUNT_ATTR =   # TYPE:varchar(200) Count Attribute
- ACCUM_ATTRS_NAME = No   # Keep Input Attributes
- List =   # List Name
- Concat =   # " " Attributes to Concatenate
- SEP = ,   # Separator Character
- Sum =   # " " Attributes to Sum
- Av =   # " " Attributes to Average
- Group_1:   # Python Script
      from re import sub
      if (FME_MacroValues['Group']==''):
          return "pyfme_none"
      else:
          group=sub(","," ",FME_MacroValues['Group'],)
          return group
- Sum_1:   # Python Script
      from re import sub
      if (FME_MacroValues['Sum']==''):
          return "pyfme_none"
      else:
          Sum=sub(","," ",FME_MacroValues['Sum'],)
          return Sum
- Concat_1:   # Python Script
      from re import sub
      if (FME_MacroValues['Concat']==''):
          return "pyfme_none"
      else:
          Concat=sub(","," ",FME_MacroValues['Concat'],)
          return Concat
- Av_1:   # Python Script
      from re import sub
      if (FME_MacroValues['Av']==''):
          return "pyfme_none"
      else:
          Av=sub(","," ",FME_MacroValues['Av'],)
          return Av
- List_1:   # Python Script
      if FME_MacroValues['List'] == "":
          return "pyfme_list"
      else:
          return FME_MacroValues['List']

Note: Refine geometry / to get all solids
GeometryRefiner
    -> AttributeExposer
Note: Expose for later removal
AttributeExposer
    ATTR_LIST = pyfme_none,pyfme_list{}
    -> GeometryFilter
GeometryCoercer_2
    KIND = fme_brep_solid
    GQUERY:
      for $geom in //geometry
      where $geom/count(parent::geometry) = 0
      return number($geom/@fme_id)
    COERCED -> Aggregator
    UNTOUCHED -> Aggregator
Note: Aggregate solids
Aggregator
    GROUP_BY = $(Group_1)
    COUNT_ATTR = $(COUNT_ATTR)
    AV = $(Av_1)
    MODE = Geometry - Assemble One Level
    AGGREGATE_TYPE = Homogeneous Collection (If Possible)
    LIST_NAME = $(List_1)
    ACCUM_ATTRS_NAME = $(ACCUM_ATTRS_NAME)
    ORDERED = No
    CONCAT_ATTRS = $(Concat_1)
    SUM = $(Sum_1)
    SEP = $(SEP)
    AGGREGATE -> BoundsExtractor
    AGGREGATE -> Clipper [CLIPPER]
Dissolved (output)
Sampler
    RATE = 1
    SAMPLE_TYPE_LONG = First N Features
    SAMPLE_MODE = No
    SAMPLED -> AttributeRemover_2
    SAMPLED -> AttributeRemover_3
    SAMPLED -> AttributeRemover_4
    SAMPLED -> AttributeRemover_5
Note: Proxies for attribute / list parameter
AttributeRemover_2
    REMOVE_ATTRS = $(Group)
AttributeRemover_3
    REMOVE_ATTRS = $(Concat)
AttributeRemover_4
    REMOVE_ATTRS = $(Sum)
AttributeRemover_5
    REMOVE_ATTRS = $(Av)
Note: Force to brep solids
GeometryCoercer
    KIND = fme_brep_solid
    GQUERY:
      for $geom in //geometry
      where $geom/count(parent::geometry) = 0
      return number($geom/@fme_id)

Bookmark: Input Data
Solids (input)
    -> GeometryRefiner
    -> Sampler

Bookmark: Filter out solids
GeometryFilter
    GEOM_PORT_NAMES = Point Line Arc Area Ellipse Text Raster "Point Cloud" Surface Solid Collection Null Instance
    BREAK_AGG = No
    POINT -> <Rejected> (output)
    LINE -> <Rejected> (output)
    ARC -> <Rejected> (output)
    AREA -> <Rejected> (output)
    ELLIPSE -> <Rejected> (output)
    TEXT -> <Rejected> (output)
    RASTER -> <Rejected> (output)
    POINTCLOUD -> <Rejected> (output)
    SURFACE -> <Rejected> (output)
    SOLID -> GeometryCoercer_2
    COLLECTION -> <Rejected> (output)
    NULL -> <Rejected> (output)
    INSTANCE -> <Rejected> (output)

Bookmark: Create bounding cube of aggregate
Note: Extract bounds
BoundsExtractor
    XMAX = _xmax
    YMAX = _ymax
    YMIN = _ymin
    ZMIN = _zmin
    ZMAX = _zmax
    XMIN = _xmin
    -> 2DBoxReplacer
Note: Replace by / bounding rectangle
2DBoxReplacer
    MINXVALATTR = @Value(_xmin)
    MINYVALATTR = @Value(_ymin)
    MAXXVALATTR = @Value(_xmax)
    MAXYVALATTR = @Value(_ymax)
    BOX -> 3DForcer
Note: Elevate bounding / rectangle by min z
3DForcer
    KEEPZVAL = No
    ZVALATTR = @Value(_zmin)
    -> Extruder_2
Note: Extrude to max z
Extruder_2
    EXTRUSION_HEIGHT = @Value(_zmax)-@Value(_zmin)
    EXTRUSION_VECTOR_INPUT = Height
    -> Clipper [CLIPPEE]

Bookmark: Clip and clean attributes
Note: Clip bounding cube by / aggregated solids to / create dissolved solid
Clipper
    CREATE_AGGREGATES = Yes
    PRESERVE_CLIPPEE_EXTENTS = No
    BOUNDARY_CASES = Treat as Inside
    CLIP_TYPE = Single Clipper
    CONNECT_Z_MODE = First Wins
    LINES_AS_SEGMENTS = No
    GROUP_BY = $(Group_1)
    INSIDE -> AttributeRemover
Note: Remove temp attributes
AttributeRemover
    LIST_ATTRS = pyfme_list{}
    REMOVE_ATTRS = pyfme_none,_xmax,_xmin,_ymax,_ymin,_zmax,_zmin
    -> Dissolved (output)

Bookmark: Rejected features ignored
<Rejected> (output)

FME custom transformer roofHeightExtractor

CoordinateExtractor_Input_1 (input)
    -> CoordinateExtractor
CoordinateExtractor
    IND = 0
    LIST_NAME = _indices
    MODE = All Coordinates
    Z_ATTR = _z
    Y_ATTR = _y
    X_ATTR = _x
    -> ListRangeExtractor
ListRangeExtractor
    MIN = _min_z_roof
    MAX = _max_z_roof
    SRC_LIST = _indices{}.z
    -> SurfaceFootprintReplacer_4
SurfaceFootprintReplacer_4
    OFFSET_Z = 0
    SHADOW_MODE = Overhead Shadow
    LIGHT_X = 0
    LIGHT_Y = 0
    LIGHT_Z = 1
    FOOTPRINT -> AreaCalculator_2
    <REJECTED> -> SurfaceFootprintReplacer_4__Rejected_
SurfaceFootprintReplacer_4__Rejected_: Inspector
AreaCalculator_2
    AREA_ATTR = _area
    MULT = 1
    AREA_TYPE = Plane Area
    -> Sorter_2
Sorter_2
    SORT_PARM = _area NUMERIC DESCENDING
    SORTED -> Counter_2
Counter_2
    DOMAIN = counter
    START = 0
    CNT_ATTR = _count_roof_area
    SCOPE = Local
    -> TestFilter_6
TestFilter_6
    TEST_LIST = BOOL_OP,OR,COMPOSITE_TEST,<Unused>,TEST_CLAUSE,"TEST @Value(_count_roof_area) = 0",LargestRoof
    DEFAULT_VALUE = <UNFILTERED>
    LargestRoof -> AttributeKeeper
Note: Removing all coordinate attributes
AttributeKeeper
    KEEP_ATTRS = _area,_max_z_roof,_min_z_roof,_count_roof_area
    -> TestFilter_6_LargestRoof (output)
TestFilter_6_LargestRoof (output)
